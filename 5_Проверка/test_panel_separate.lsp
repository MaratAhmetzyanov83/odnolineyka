;;; Separate objects with native DWG entities. COM explosion is adapted to native EXPLODE in Core Console.
(defun qa:check (label ok) (write-line (strcat label "=" (if ok "PASS" "FAIL")) qa:panel-report))
(defun qa:fixture (point / name)
  (if (null (tblsearch "BLOCK" "CP_QA_DEVICE"))
    (progn
      (entmake '((0 . "BLOCK") (2 . "CP_QA_DEVICE") (70 . 0) (10 0.0 0.0 0.0)))
      (entmake '((0 . "LINE") (10 0.0 0.0 0.0) (11 18.0 90.0 0.0)))
      (entmake '((0 . "ATTDEF") (10 1.0 80.0 0.0) (40 . 4.0) (1 . "QF") (2 . "ID") (3 . "ID") (70 . 0)))
      (entmake '((0 . "ENDBLK")))
      (entmake '((0 . "BLOCK") (2 . "CP_QA_LAYOUT") (70 . 0) (10 0.0 0.0 0.0)))
      (entmake '((0 . "TEXT") (10 0.0 120.0 0.0) (40 . 6.0) (1 . "QA layout")))
      (entmake '((0 . "INSERT") (2 . "CP_QA_DEVICE") (66 . 1) (10 0.0 0.0 0.0)))
      (entmake '((0 . "ATTRIB") (10 1.0 80.0 0.0) (40 . 4.0) (1 . "QF7") (2 . "ID") (70 . 0)))
      (entmake '((0 . "SEQEND")))
      (entmake '((0 . "TEXT") (10 0.0 100.0 0.0) (40 . 4.0) (1 . "QF7")))
      (entmake '((0 . "ENDBLK")))))
  (entmake (list '(0 . "INSERT") '(2 . "CP_QA_LAYOUT") (cons 10 point))) (entlast))
(defun qa:separate ( / cp:cfg cp:newdef cp:pendingparts cp:pendinggroup cp:pendingnew cp:failure vla-explode vla-delete vlax-vla-object->ename
                       source frame parts members record id other copy picked ss entity data device anchor before failure created)
  (defun vlax-vla-object->ename (object) object)
  (defun vla-delete (object) (entdel object))
  (defun vla-explode (object)
    (vl-cmdf "_.EXPLODE" object)
    ;; ActiveX Explode leaves its original reference intact; restore the native command's erased source.
    (entdel object) nil)
  (vl-cmdf "_.UCS" "_World")
  (setq cp:cfg '((oneblock) (panel . "QA") (textheight . 4.0) (xttextheight . 2.0))
        source (qa:fixture '(100.0 200.0 0.0)) frame '((100.0 200.0 0.0) 1.0 1.0 1.0 0.0))
  (entmake '((0 . "TEXT") (10 999.0 999.0 0.0) (40 . 4.0) (1 . "Unrelated")))
  (setq other (entlast) parts (cp:separate source frame) members (caddr parts) id (cadr parts) record (vlax-ldata-get cp:partsapp id))
  (qa:check "outer_layout_removed" (null (entget source)))
  (qa:check "three_top_level_objects_created" (= (length members) 3))
  (qa:check "unrelated_entity_preserved" (entget other))
  (qa:check "device_remains_a_block" (setq device (car (vl-remove-if-not '(lambda (e) (= (cdr (assoc 0 (entget e))) "INSERT")) members))))
  (qa:check "device_attribute_QF7_preserved" (= (cdr (assoc 1 (entget (entnext device)))) "QF7"))
  (qa:check "captions_are_separate_text" (= (length (vl-remove-if-not '(lambda (e) (= (cdr (assoc 0 (entget e))) "TEXT")) members)) 2))
  (qa:check "registry_keeps_settings" (equal (cdr (assoc 'settings record)) cp:cfg))
  (qa:check "original_frame_preserved" (equal (cp:parts-frame id record) frame 0.00001))
  (qa:check "pick_from_device_resolves_entire_layout" (and (setq picked (cp:parts-pick device)) (equal (caddar picked) members)))
  (qa:check "pick_from_caption_resolves_entire_layout" (and (setq picked (cp:parts-pick (car members))) (equal (cadr picked) cp:cfg)))
  (setq ss (ssadd)) (foreach entity members (ssadd entity ss))
  (vl-cmdf "_.MOVE" ss "" "_non" '(0.0 0.0 0.0) "_non" '(10.0 20.0 0.0))
  (qa:check "moving_layout_preserves_new_origin" (equal (car (cp:parts-frame id record)) '(110.0 220.0 0.0) 0.00001))
  (vl-cmdf "_.ROTATE" ss "" "_non" '(110.0 220.0 0.0) 90.0)
  (qa:check "rotating_layout_preserves_origin_and_angle"
    (and (equal (car (cp:parts-frame id record)) '(110.0 220.0 0.0) 0.00001) (equal (nth 4 (cp:parts-frame id record)) (/ pi 2.0) 0.00001)))
  (vl-cmdf "_.SCALE" ss "" "_non" '(110.0 220.0 0.0) 2.0)
  (qa:check "scaling_layout_preserves_frame"
    (equal (cp:parts-frame id record) (list '(110.0 220.0 0.0) 2.0 2.0 2.0 (/ pi 2.0)) 0.00001))
  (entmake (entget (car members) (list cp:partsapp)))
  (setq copy (entlast))
  (qa:check "copied_component_cannot_target_original_layout" (null (cp:parts-pick copy)))
  (entdel (car members))
  (qa:check "manually_deleted_member_is_skipped" (= (length (cp:parts-entities id record)) 2))
  (qa:check "deleted_title_falls_back_to_device_frame"
    (equal (cp:parts-frame id record) (list '(110.0 220.0 0.0) 2.0 2.0 2.0 (/ pi 2.0)) 0.00001))
  (cp:container-delete parts)
  (qa:check "delete_removes_all_remaining_members" (vl-every '(lambda (e) (null (entget e))) members))
  (qa:check "delete_removes_registry" (null (vlax-ldata-get cp:partsapp id)))
  (qa:check "delete_preserves_copy_and_unrelated_entity" (and (entget copy) (entget other)))
  (setq cp:pendingparts nil cp:pendinggroup nil source (qa:fixture '(0.0 0.0 0.0)))
  (defun vla-explode (object) nil)
  (setq failure (vl-catch-all-apply 'cp:separate (list source frame)))
  (qa:check "empty_explosion_is_rejected" (vl-catch-all-error-p failure))
  (qa:check "failed_explosion_keeps_source" (and (entget source) (null cp:pendingparts)))
  (defun vla-explode (object) (entmake '((0 . "TEXT") (10 0.0 0.0 0.0) (40 . 4.0) (1 . "Rollback"))) nil)
  (defun vla-delete (object) (/ 1 0))
  (setq cp:failure nil failure (vl-catch-all-apply 'cp:separate (list source frame)) created cp:pendingparts id cp:pendinggroup)
  (qa:check "source_delete_failure_is_caught" (vl-catch-all-error-p failure))
  (cp:cleanup-new)
  (qa:check "rollback_keeps_source_and_removes_new_parts" (and (entget source) (vl-every '(lambda (e) (null (entget e))) created)))
  (qa:check "rollback_removes_pending_registry" (null (vlax-ldata-get cp:partsapp id))))
(qa:separate)
(defun qa:output-mode ( / cp:cfg cp:panels get_tile set_tile done_dialog qa:mode)
  (defun get_tile (key)
    (cond ((= key "oneblock") qa:mode) ((= key "panel") "0") ((= key "library") "QA.dwg")
          ((= key "reserve") "20") ((= key "nrows") "2") ((= key "slots") "24") ((= key "pitch") "18")
          ((= key "railpitch") "150") ((= key "devh") "90") ((= key "textheight") "4") ((= key "xttextheight") "2")))
  (defun set_tile (key value) nil)
  (defun done_dialog (result) nil)
  (setq cp:cfg nil cp:panels '("QA") qa:mode "0")
  (cp:cfg-save)
  (qa:check "unchecked_toggle_selects_separate_objects" (and (assoc 'oneblock cp:cfg) (not (cp:g 'oneblock))))
  (setq qa:mode "1") (cp:cfg-save)
  (qa:check "checked_toggle_selects_single_block" (cp:g 'oneblock)))
(qa:output-mode)
(defun qa:commands ( / cp:defaults cp:pick cp:build cp:block-frame cp:read-book cp:import-library cp:collect cp:apply-sizes cp:sizes-dialog cp:plan cp:dialog
                       getpoint vlax-get-acad-object vla-get-activedocument vla-startundomark vla-endundomark vla-regen
                       vla-put-xscalefactor vla-put-yscalefactor vla-put-zscalefactor vla-put-rotation vla-delete vla-explode vlax-vla-object->ename
                       qa:pick qa:mode qa:path qa:file wrapper old parts next cfg frame layer data failure)
  (defun vlax-get-acad-object () "QA")
  (defun vla-get-activedocument (app) "QA")
  (defun vla-startundomark (doc) nil)
  (defun vla-endundomark (doc) nil)
  (defun vla-regen (doc mode) nil)
  (defun vlax-vla-object->ename (object) object)
  (defun vla-delete (object) (entdel object))
  (defun vla-explode (object) (vl-cmdf "_.EXPLODE" object) (entdel object) nil)
  (defun qa:set-property (object code value / data)
    (setq data (entget object))
    (entmod (if (assoc code data) (subst (cons code value) (assoc code data) data) (append data (list (cons code value))))))
  (defun vla-put-xscalefactor (object value) (qa:set-property object 41 value))
  (defun vla-put-yscalefactor (object value) (qa:set-property object 42 value))
  (defun vla-put-zscalefactor (object value) (qa:set-property object 43 value))
  (defun vla-put-rotation (object value) (qa:set-property object 50 value))
  (defun cp:block-frame (object / data)
    (setq data (entget object))
    (list (cdr (assoc 10 data)) (cdr (assoc 41 data)) (cdr (assoc 42 data)) (cdr (assoc 43 data)) (cdr (assoc 50 data))))
  (defun cp:defaults () (list (cons 'path qa:path) '(panel . "QA") '(oneblock . T)))
  (defun cp:pick () qa:pick)
  (defun getpoint (prompt) '(100.0 200.0 0.0))
  (defun cp:read-book (path) (setq cp:panels '("QA")))
  (defun cp:import-library () nil)
  (defun cp:collect (panel) (setq cp:devices nil cp:terminals nil))
  (defun cp:apply-sizes () nil)
  (defun cp:sizes-dialog () T)
  (defun cp:plan () T)
  (defun cp:dialog () (cp:put 'oneblock qa:mode) T)
  (defun cp:build (point) (setq cp:pendingnew (qa:fixture point)))
  (setq qa:path (strcat (getenv "TEMP") "/cpdraw_command_qa_" (itoa (abs (getvar "MILLISECS"))) ".txt") qa:file (open qa:path "w"))
  (write-line "QA" qa:file) (close qa:file)
  (setq qa:mode T)
  (cp:run nil T)
  (setq wrapper (entlast) cfg cp:cfg frame (cp:block-frame wrapper) qa:pick (list wrapper cfg frame))
  (qa:check "CPDRAW_checked_creates_outer_block" (= (cdr (assoc 2 (entget wrapper))) "CP_QA_LAYOUT"))
  (c:CPEXPLODE)
  (setq parts (cp:parts-pick (entlast)))
  (qa:check "CPEXPLODE_converts_existing_layout" (and (null (entget wrapper)) parts (not (cdr (assoc 'oneblock (cadr parts))))))
  (setq qa:pick parts old (car parts))
  (cp:run T nil)
  (setq next (cp:parts-pick (entlast)))
  (qa:check "CPUPDATE_replaces_separate_objects" (and next (vl-every '(lambda (e) (null (entget e))) (caddr old)) (null (vlax-ldata-get cp:partsapp (cadr old)))))
  (setq qa:pick next old (car next) qa:mode T)
  (cp:run T T)
  (setq wrapper (entlast) qa:pick (list wrapper cp:cfg (cp:block-frame wrapper)))
  (qa:check "CPEDIT_can_restore_single_block" (and (= (cdr (assoc 2 (entget wrapper))) "CP_QA_LAYOUT") (vl-every '(lambda (e) (null (entget e))) (caddr old))))
  (setq qa:mode nil)
  (cp:run T T)
  (setq next (cp:parts-pick (entlast)))
  (qa:check "CPEDIT_can_switch_back_to_separate_objects" (and next (null (entget wrapper)) (equal (car (caddr next)) '(100.0 200.0 0.0) 0.00001)))
  (setq old (car next) qa:mode nil)
  (cp:run nil T)
  (setq next (cp:parts-pick (entlast)))
  (qa:check "CPDRAW_unchecked_creates_separate_objects" (and next (not (cdr (assoc 'oneblock (cadr next))))))
  (qa:check "new_layout_preserves_existing_layout" (vl-every 'entget (caddr old)))
  (setq qa:pick next parts (car next))
  (c:CPDELETE)
  (qa:check "CPDELETE_removes_only_selected_separate_layout" (and (vl-every '(lambda (e) (null (entget e))) (caddr parts)) (vl-every 'entget (caddr old))))
  (entmake '((0 . "LAYER") (2 . "CP_QA_LOCKED") (70 . 0) (62 . 7)))
  (setq data (entget (cadr (caddr old))))
  (entmod (subst '(8 . "CP_QA_LOCKED") (assoc 8 data) data))
  (setq layer (tblobjname "LAYER" "CP_QA_LOCKED") data (entget layer))
  (entmod (subst '(70 . 4) (assoc 70 data) data))
  (setq failure (vl-catch-all-apply 'cp:container-delete (list old)))
  (qa:check "locked_member_prevents_partial_deletion" (and (vl-catch-all-error-p failure) (vl-every 'entget (caddr old))))
  (qa:check "failed_delete_keeps_layout_registry" (vlax-ldata-get cp:partsapp (cadr old)))
  (setq data (entget layer)) (entmod (subst '(70 . 0) (assoc 70 data) data))
  (cp:container-delete old)
  (vl-file-delete qa:path))
(qa:commands)
(princ)
