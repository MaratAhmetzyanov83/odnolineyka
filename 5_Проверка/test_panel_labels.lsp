;;; Размеры подписей: значения по умолчанию, ввод, отрисовка и сохранение в своей копии DWG.
(defun qa:check (label ok)
  (write-line (strcat label "=" (if ok "PASS" "FAIL")) qa:panel-report))
(defun qa:label-defaults ( / vlax-ldata-get qa:last cfg)
  (defun vlax-ldata-get (dictionary key) qa:last)
  (setq cfg (cp:defaults))
  (qa:check "fresh_caption_defaults_4_and_2" (and (= (cdr (assoc 'textheight cfg)) 4.0) (= (cdr (assoc 'xttextheight cfg)) 2.0)))
  (setq qa:last '((nrows . 2) (devh . 90.0) (gap . 60.0) (library . "QA.dwg") (path . "QA.xlsx") (panel . "QA")) cfg (cp:defaults))
  (qa:check "legacy_settings_get_caption_defaults" (and (= (cdr (assoc 'textheight cfg)) 4.0) (= (cdr (assoc 'xttextheight cfg)) 2.0)))
  (setq qa:last (append '((textheight . 5.5) (xttextheight . 1.8)) qa:last) cfg (cp:defaults))
  (qa:check "saved_caption_sizes_preserved" (and (= (cdr (assoc 'textheight cfg)) 5.5) (= (cdr (assoc 'xttextheight cfg)) 1.8))))
(qa:label-defaults)
(defun qa:label-input ( / cp:cfg cp:panels get_tile set_tile done_dialog qa:tiles qa:result qa:status key value original)
  (defun get_tile (key) (cdr (assoc key qa:tiles)))
  (defun set_tile (key value) (setq qa:status value))
  (defun done_dialog (result) (setq qa:result result))
  (setq cp:cfg nil cp:panels '("QA")
        qa:tiles '(("nrows" . "2") ("slots" . "24") ("pitch" . "18") ("reserve" . "20") ("devh" . "90") ("railpitch" . "150")
                   ("textheight" . "5,5") ("xttextheight" . "2.5") ("oneblock" . "1") ("library" . "QA.dwg") ("panel" . "0")))
  (cp:cfg-save)
  (qa:check "caption_input_accepts_comma_and_dot" (and (= qa:result 1) (= (cp:g 'textheight) 5.5) (= (cp:g 'xttextheight) 2.5)))
  (foreach key '("textheight" "xttextheight")
    (setq original (assoc key qa:tiles))
    (foreach value '("0" "-10" "abc")
      (setq qa:result nil qa:status nil qa:tiles (subst (cons key value) (assoc key qa:tiles) qa:tiles))
      (cp:cfg-save)
      (qa:check (strcat "caption_input_rejects_" key "_" value) (and (null qa:result) qa:status)))
    (setq qa:tiles (subst original (assoc key qa:tiles) qa:tiles))))
(qa:label-input)
(defun qa:label-drawing ( / cp:cfg cp:devices cp:terminalgroups cp:cross-counts cp:cross-unknown cp:measure cp:place-block cp:text cp:draw-list vla-get-hasattributes vla-put-rotation qa:captions before row i)
  (defun cp:measure (name scale angle state) (list 0.0 0.0 (if (wcmatch name "D-VPR-*") 2.2 6.2) 55.9))
  (defun cp:place-block (mapping x y layer id) nil)
  (defun cp:text (x y height text width layer) (setq qa:captions (cons (list text height) qa:captions)) nil)
  (defun cp:draw-list (x top) nil)
  (defun vla-get-hasattributes (object) :vlax-false)
  (defun vla-put-rotation (object angle) nil)
  (setq cp:cfg '((nrows . 2) (slots . 2) (pitch . 18.0) (reserve . 0.0) (gap . 60.0) (devh . 90.0) (railpitch . 150.0) (panel . "QA") (textheight . 5.5) (xttextheight . 2.5))
        cp:devices '(("QF1" "QF" "AV_2P_36" 2.0 90.0 "QF" 3 "AV_2P_36" 1.0 0.0)
                     ("QF2" "QF" "AV_2P_36" 2.0 90.0 "QF" 4 "AV_2P_36" 1.0 0.0))
        cp:terminalgroups nil cp:cross-counts '(0 0 0 0) cp:cross-unknown 0 i 44)
  (repeat 44 (setq row (cons (cond ((= i 17) "3x4") ((= i 22) "L1") ((= i 44) 1)) row) i (1- i)))
  (cp:terminal-set "XT1" row)
  (cp:plan)
  (setq before (list cp:positions cp:xtpositions cp:rowpitch (cp:g 'h)))
  (cp:draw-geometry)
  (qa:check "device_captions_draw_at_5_5" (and (= (cadr (assoc "QF1" qa:captions)) 5.5) (= (cadr (assoc "QF2" qa:captions)) 5.5)))
  (qa:check "all_terminal_captions_draw_at_2_5" (vl-every '(lambda (id) (= (cadr (assoc id qa:captions)) 2.5)) '("XT1:L" "XT1:N" "XT1:PE")))
  (cp:put 'textheight 7.0) (cp:put 'xttextheight 3.5)
  (cp:plan)
  (qa:check "caption_edit_preserves_layout_and_rail_axes" (equal before (list cp:positions cp:xtpositions cp:rowpitch (cp:g 'h)) 0.00001))
  (setq qa:captions nil)
  (cp:draw-geometry)
  (qa:check "edited_device_caption_is_7" (= (cadr (assoc "QF1" qa:captions)) 7.0))
  (qa:check "edited_terminal_caption_is_3_5" (= (cadr (assoc "XT1:PE" qa:captions)) 3.5))
  (vlax-ldata-put "CP_LABEL_QA" "settings" cp:cfg)
  (qa:check "caption_sizes_roundtrip_through_DWG" (and (= (cdr (assoc 'textheight (vlax-ldata-get "CP_LABEL_QA" "settings"))) 7.0)
                                                     (= (cdr (assoc 'xttextheight (vlax-ldata-get "CP_LABEL_QA" "settings"))) 3.5)))
  (setq cp:cfg (vl-remove-if '(lambda (p) (member (car p) '(textheight xttextheight))) cp:cfg) qa:captions nil)
  (cp:draw-geometry)
  (qa:check "legacy_update_draws_old_caption_sizes" (and (= (cadr (assoc "QF1" qa:captions)) 4.0) (= (cadr (assoc "XT1:L" qa:captions)) 2.0))))
(qa:label-drawing)
(princ)
