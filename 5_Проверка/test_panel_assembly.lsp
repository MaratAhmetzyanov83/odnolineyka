;;; v2.0: номинал с кириллицей, фазы по кругу, отрезки гребёнок, кросс-модуль по гребёнкам, сечение, провода.
(defun qa:check (label ok)
  (write-line (strcat label "=" (if ok "PASS" "FAIL")) qa:panel-report))
;;; Номинал: «С16А» (кириллица С и А), «QS 3P 80А».
(qa:check "cyrillic_rating_C16A" (equal (cp:qparts (strcat "2P " (cp:ru '(1057)) "16" (cp:ru '(1040)) " 30" (cp:ru '(1084 1040)))) '("2P" 16.0 T)))
(qa:check "qs_rating_80A" (equal (cp:qparts (strcat "QS 3P 80" (cp:ru '(1040)))) '("3P" 80.0 nil)))
(qa:check "latin_rating_unchanged" (equal (cp:qparts "1P C10A") '("1P" 10.0 nil)))
(qa:check "curve_from_cyrillic" (= (cp:curve (strcat "1P " (cp:ru '(1057)) "10")) "C"))
;;; Фазы по кругу: из таблицы L1 L1 L2 L3 L3 и одна без фазы.
(defun qa:dev (id poles phase diff)
  (cp:inf-put id 'poles poles) (cp:inf-put id 'phase phase) (cp:inf-put id 'diff diff) (cp:inf-put id 'aphase nil)
  (list id "QF" "AV" (if (or diff (= poles "2P")) 2.0 1.0) 90.0 "QF" 3 "AV" 1.0 0.0 nil))
(defun qa:cycle ( / cp:info devs order)
  (setq devs (list (qa:dev "A" "1P" "L1" nil) (qa:dev "B" "1P" "L1" nil) (qa:dev "C" "1P" "L2" nil)
                   (qa:dev "D" "1P" "L3" nil) (qa:dev "E" "1P" "L3" nil) (qa:dev "F" "1P" "" nil)))
  (setq order (cp:cycle devs))
  (qa:check "cycle_order" (equal (mapcar 'car order) '("A" "C" "D" "B" "F" "E")))
  (qa:check "cycle_phases" (equal (mapcar '(lambda (d) (cp:inf (car d) 'aphase)) order) '("L1" "L2" "L3" "L1" "L2" "L3")))
  (qa:check "cycle_marks_assumed" (and (cp:inf "F" 'assumed) (not (cp:inf "A" 'assumed)))))
(qa:cycle)
;;; Раскладка: ввод и кросс-модуль первыми, отрезки гребёнок по рейкам, плотная раскладка не рвёт круг.
(defun qa:segments ( / cp:info cp:cfg cp:devices cp:positions cp:segs packed)
  (setq cp:cfg '((slots . 6) (pitch . 18.0) (reserve . 0.0) (comb . T) (dense . T) (npe . T))
        cp:devices (list (qa:dev "Q1" "1P" "L1" nil) (qa:dev "Q2" "1P" "L2" nil) (qa:dev "Q3" "1P" "L3" nil)
                         (qa:dev "D1" "2P" "L1" T) (qa:dev "D2" "2P" "L2" T) (qa:dev "D3" "2P" "L3" T)
                         (list "MK1" "MK" "MK" 1.0 90.0 "MK" 3 "MK" 1.0 0.0 nil)))
  (cp:arrange)
  (qa:check "arrange_classes" (equal (mapcar 'car cp:devices) '("D1" "D2" "D3" "Q1" "Q2" "Q3" "MK1")))
  (setq packed (cp:pack cp:devices 108.0 18.0) cp:positions (car packed))
  (qa:check "pack_rows" (= (cadr packed) 2))
  (qa:check "classes_on_rails" (equal (mapcar '(lambda (p) (list (car (car p)) (cadr p))) cp:positions)
                                               '(("D1" 0) ("D2" 0) ("D3" 0) ("Q1" 1) ("Q2" 1) ("Q3" 1) ("MK1" 1))))
  (cp:segments)
  (qa:check "segments" (equal (mapcar '(lambda (s) (list (car s) (cadr s) (length (nth 4 s)))) cp:segs) '(("1PN" 0 3) ("1P" 1 3))))
  (qa:check "comb_counts" (equal (cp:comb-counts) '(2 2 2 1))))
(qa:segments)
;;; Сечение по номиналу, цвета по умолчанию.
(setq cp:asm nil)
(qa:check "section_10A" (= (cp:section 10.0) 1.5))
(qa:check "section_16A" (= (cp:section 16.0) 2.5))
(qa:check "section_50A" (= (cp:section 50.0) 16.0))
(qa:check "section_unknown_is_smallest" (= (cp:section nil) 1.5))
(qa:check "color_L1_white" (= (cp:color "L1") (cp:ru '(1073 1077 1083 1099 1081))))
;;; Провода: аппарат 1P -> клемма L, N и PE из модуля N/PE.
(defun qa:wires ( / cp:info cp:devices cp:segs cp:posmapl cp:wirelist cp:asm)
  (setq cp:devices (list (list "XNP1" "NPE|X" "X" 6.0 90.0 "NPE" 0) (qa:dev "QF1" "1P" "L2" nil)))
  (cp:inf-put "QF1" 'amp 10.0) (cp:inf-put "QF1" 'tids '("XT1"))
  (setq cp:posmapl '(("XNP1" 0.0 100.0 100.0 90.0) ("QF1" 200.0 100.0 18.0 90.0) ("XT1" 200.0 -50.0 5.2 103.0)))
  (cp:wires)
  (qa:check "wires_L_N_PE" (equal (mapcar '(lambda (w) (list (car w) (cadr w) (caddr w) (nth 4 w))) cp:wirelist)
                                  '(("QF1" "XT1" "L2" 1.5) ("XNP1" "XT1" "N" 1.5) ("XNP1" "XT1" "PE" 1.5))))
  (qa:check "wire_length_route_plus_reserve" (equal (nth 5 (car cp:wirelist)) 209.9 0.01)))
(qa:wires)
(princ)
