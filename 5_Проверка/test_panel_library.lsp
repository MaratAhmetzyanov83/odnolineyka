;;; Загрузить SX_Panel.lsp, затем этот файл. Проверяем тип и порядок поиска пути.
;;; Подмены FINDFILE / GETENV локальны для одного случая; настройки AutoCAD не меняются.
(defun qa:panel-library-case (label files cached expected / findfile getenv result)
  (defun findfile (path)
    (if (/= (type path) 'STR) (exit))
    (if (= path "SX_Panel.lsp") (setq path qa:panel-source))
    (if (member path files) path))
  (defun getenv (key) (if (= key "CP_DclFile") cached))
  (setq result (vl-catch-all-apply 'cp:default-library nil))
  (write-line
    (strcat label "=" (if (and (not (vl-catch-all-error-p result)) (equal result expected)) "PASS" "FAIL")) qa:panel-report)
  (if (vl-catch-all-error-p result)
    (write-line (vl-catch-all-error-message result) qa:panel-report)))
(setq qa:panel-source (cp:ru '(67 58 47 67 80 95 84 69 83 84 47 1050 1086 1084 1087 1086 1085 1086 1074 1082 1072 47 83 88 95 80 97 110 101 108 46 108 115 112))
      qa:panel-dcl (cp:ru '(67 58 47 67 80 95 84 69 83 84 47 1050 1086 1084 1087 1086 1085 1086 1074 1082 1072 47 83 88 95 80 97 110 101 108 46 100 99 108))
      qa:panel-local (cp:ru '(67 58 47 67 80 95 84 69 83 84 47 1050 1086 1084 1087 1086 1085 1086 1074 1082 1072 47 46 46 47 1041 1083 1086 1082 1080 47 83 88 95 1050 1086 1084 1087 1086 1085 1086 1074 1082 1072 95 1087 1086 1083 1100 1079 1086 1074 1072 1090 1077 1083 1100 1089 1082 1080 1077 46 100 119 103))
      qa:panel-google (cp:ru '(71 58 47 1052 1086 1081 32 1076 1080 1089 1082 47 1054 1076 1085 1086 1083 1080 1085 1077 1081 1082 1072 95 1073 1072 1079 1099 47 83 88 95 1050 1086 1084 1087 1086 1085 1086 1074 1082 1072 95 1087 1086 1083 1100 1079 1086 1074 1072 1090 1077 1083 1100 1089 1082 1080 1077 46 100 119 103)))
(qa:panel-library-case "support_local_path_is_string" (list qa:panel-source qa:panel-local) nil qa:panel-local)
(qa:panel-library-case "cached_dcl_local_path_is_string" (list qa:panel-dcl qa:panel-local) qa:panel-dcl qa:panel-local)
(qa:panel-library-case "local_precedes_google" (list qa:panel-source qa:panel-local qa:panel-google) nil qa:panel-local)
(qa:panel-library-case "google_when_local_missing" (list qa:panel-source qa:panel-google) nil qa:panel-google)
(qa:panel-library-case "google_when_cached_dcl_and_local_missing" (list qa:panel-dcl qa:panel-google) qa:panel-dcl qa:panel-google)
(qa:panel-library-case "google_without_local_folder" (list qa:panel-google) nil qa:panel-google)
(qa:panel-library-case "missing_files_return_nil" nil nil nil)
(qa:panel-library-case "stale_cached_dcl_falls_back_to_google" (list qa:panel-google) qa:panel-dcl qa:panel-google)
(princ)
