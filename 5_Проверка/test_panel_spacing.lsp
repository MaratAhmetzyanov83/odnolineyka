;;; Проверка межосевого шага и сохранения в собственной копии DWG.
(defun qa:check (label ok)
  (write-line (strcat label "=" (if ok "PASS" "FAIL")) qa:panel-report))
(qa:check "fresh_default_is_150" (= (cp:railpitch-default nil) 150.0))
(qa:check "legacy_custom_gap_migrates" (= (cp:railpitch-default '((devh . 100.0) (gap . 80.0))) 180.0))
(qa:check "explicit_spacing_preserved" (= (cp:railpitch-default '((railpitch . 125.5) (devh . 200.0) (gap . 80.0))) 125.5))
(defun qa:row ( / i row)
  (setq i 44)
  (repeat 44 (setq row (cons (cond ((= i 8) "1P C16A") ((= i 17) "3x2.5") ((= i 22) "L1") ((= i 44) 1)) row) i (1- i))) row)
(defun qa:spacing-plan ( / cp:cfg cp:devices cp:terminalgroups cp:measure qa:height)
  (defun cp:measure (name scale angle state)
    (list 0.0 0.0 (if (= name "D-VPR-2.5-3L") 2.2 5.2) qa:height))
  (setq qa:height 103.0 cp:cfg '((nrows . 2) (slots . 1) (pitch . 18.0) (reserve . 0.0) (gap . 60.0) (devh . 90.0) (railpitch . 120.0))
        cp:devices '(("QF1" "QF" "AV_1P_18" 1.0 90.0 "QF" 3 "AV_1P_18" 1.0 0.0)
                     ("QF2" "QF" "AV_1P_18" 1.0 90.0 "QF" 4 "AV_1P_18" 1.0 0.0))
        cp:terminalgroups nil)
  (cp:terminal-set "XT1" (qa:row))
  (qa:check "two_device_rows_and_one_terminal_row_fit" (and (cp:plan) (= cp:totalrows 3)))
  (qa:check "device_row_axes_120" (equal (- (cp:yc 0) (cp:yc 1)) 120.0 0.00001))
  (qa:check "terminal_row_axis_120" (equal (- (cp:yc 1) (cp:yc 2)) 120.0 0.00001))
  (qa:check "total_height_at_120" (equal (cp:g 'h) 343.0 0.00001))
  (setq qa:height 203.0)
  (cp:plan)
  (qa:check "taller_blocks_do_not_change_axes" (equal (- (cp:yc 1) (cp:yc 2)) 120.0 0.00001))
  (qa:check "taller_blocks_change_outer_height" (equal (cp:g 'h) 443.0 0.00001))
  (cp:put 'railpitch 240.0)
  (cp:plan)
  (qa:check "edited_spacing_is_240" (equal (- (cp:yc 0) (cp:yc 1)) 240.0 0.00001))
  (setq cp:cfg (vl-remove-if '(lambda (p) (= (car p) 'railpitch)) cp:cfg))
  (cp:plan)
  (qa:check "legacy_update_keeps_old_height_plus_gap" (equal cp:rowpitch 263.0 0.00001)))
(qa:spacing-plan)
(defun qa:spacing-input ( / cp:cfg cp:panels get_tile set_tile done_dialog qa:tiles qa:result qa:status)
  (defun get_tile (key) (cdr (assoc key qa:tiles)))
  (defun set_tile (key value) (setq qa:status value))
  (defun done_dialog (result) (setq qa:result result))
  (setq cp:cfg nil cp:panels '("QA")
        qa:tiles '(("nrows" . "2") ("slots" . "24") ("pitch" . "18") ("reserve" . "20") ("devh" . "90") ("railpitch" . "125,5") ("textheight" . "4") ("xttextheight" . "2") ("oneblock" . "1") ("library" . "QA.dwg") ("panel" . "0")))
  (cp:cfg-save)
  (qa:check "dialog_accepts_fraction_with_comma" (and (= qa:result 1) (equal (cp:g 'railpitch) 125.5 0.00001)))
  (foreach value '("0" "-10" "abc")
    (setq qa:result nil qa:status nil qa:tiles (subst (cons "railpitch" value) (assoc "railpitch" qa:tiles) qa:tiles))
    (cp:cfg-save)
    (qa:check (strcat "dialog_rejects_spacing_" value) (and (null qa:result) qa:status))))
(qa:spacing-input)
(defun qa:drawn-layout ( / cp:cfg cp:devices cp:rows cp:terminalgroups cp:cross-counts cp:cross-unknown cp:measure cp:place-block cp:text cp:draw-list vla-get-hasattributes vla-put-rotation qa:placed y1 y2 yt)
  (defun cp:measure (name scale angle state)
    (list 0.0 0.0 (if (= name "D-VPR-2.5-3L") 2.2 5.2) 103.0))
  (defun cp:place-block (mapping x y layer id) (setq qa:placed (cons (list (car mapping) y) qa:placed)) nil)
  (defun cp:text (x y height text width layer) nil)
  (defun cp:draw-list (x top) nil)
  (defun vla-get-hasattributes (object) :vlax-false)
  (defun vla-put-rotation (object angle) nil)
  (setq cp:cfg '((nrows . 2) (slots . 1) (pitch . 18.0) (reserve . 0.0) (gap . 60.0) (devh . 90.0) (railpitch . 125.5) (panel . "QA"))
        cp:devices '(("QF1" "QF" "AV_1P_18" 1.0 90.0 "QF" 3 "AV_1P_18" 1.0 0.0)
                     ("QF2" "QF" "AV_1P_18" 1.0 90.0 "QF" 4 "AV_1P_18" 1.0 0.0))
        cp:rows (list (qa:row) (qa:row)) cp:terminalgroups nil cp:cross-counts '(0 0 0 0) cp:cross-unknown 0)
  (cp:terminal-set "XT1" (qa:row))
  (qa:check "fractional_spacing_layout_fits" (cp:plan))
  (cp:draw-geometry)
  (setq qa:placed (reverse qa:placed) y1 (cadar qa:placed) y2 (cadadr qa:placed)
        yt (cadr (car (vl-remove-if-not '(lambda (d) (= (car d) "VPR-2.5-3L-GY")) qa:placed))))
  (qa:check "drawing_places_device_axes_at_125_5" (equal (- y1 y2) 125.5 0.00001))
  (qa:check "drawing_places_terminal_axis_at_125_5" (equal (- y2 yt) 125.5 0.00001))
  (vlax-ldata-put "CP_SPACING_QA" "settings" cp:cfg)
  (qa:check "spacing_roundtrips_through_DWG_settings" (equal (cdr (assoc 'railpitch (vlax-ldata-get "CP_SPACING_QA" "settings"))) 125.5 0.00001)))
(qa:drawn-layout)
(princ)
