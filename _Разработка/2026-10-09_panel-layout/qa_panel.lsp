(vl-load-com)
(if (= (getvar "DWGNAME") "Компоновка_проверка_из_базы.dwg")
(progn
(load "C:/Users/user/Desktop/02_Справочники_CAD_Revit/odnolineyka/2_AutoCAD/Компоновка/SX_Panel.lsp")
(setq qf (open "C:/Users/user/Desktop/02_Справочники_CAD_Revit/odnolineyka/_Разработка/2026-10-09_panel-layout/qa_result.txt" "w"))
(defun qa:check (key ok) (write-line (strcat key "=" (if ok "PASS" "FAIL")) qf))
(defun *error* (msg) (write-line (strcat "ERROR=" msg " STAGE=" (if qa:stage qa:stage "unknown")) qf) (close qf) (princ))
(setq qa:stage "root")
(setq cp:doc (vla-get-activedocument (vlax-get-acad-object))
      qa:root (vla-item (vla-get-modelspace cp:doc) 0)
      cp:cfg (vlax-ldata-get qa:root "settings"))
(setq qa:stage "book") (cp:read-book (cp:g 'path))
(setq qa:stage "library") (cp:import-library)
(setq qa:stage "collect") (cp:collect (cp:g 'panel)) (cp:apply-sizes)
(setq qa:stage "plan")
(qa:check "plan" (cp:plan))
(setq qa:ok T qa:lastrow -1 qa:right 0.0)
(foreach pp cp:positions
  (if (= (cadr pp) qa:lastrow)
    (if (< (nth 2 pp) (- qa:right 0.001)) (setq qa:ok nil)))
  (setq qa:lastrow (cadr pp) qa:right (+ (nth 2 pp) (* (nth 3 (car pp)) (cp:g 'pitch)))))
(qa:check "no_overlaps" qa:ok)
(setq qa:xttight T qa:xtrow -1 qa:xtright 0.0)
(foreach pos cp:xtpositions
  (if (= (cadr pos) qa:xtrow)
    (if (not (equal (nth 2 pos) qa:xtright 0.00001)) (setq qa:xttight nil)))
  (setq qa:xtrow (cadr pos) qa:xtright (+ (nth 2 pos) (nth 3 (car pos)))))
(qa:check "terminals_and_endcaps_touch" qa:xttight)
(setq qa:slots (cp:g 'slots)) (cp:put 'slots 2)
(qa:check "oversize_rejected" (not (cp:plan))) (cp:put 'slots qa:slots)
(setq qa:nrows (cp:g 'nrows)) (cp:put 'nrows 1)
(qa:check "row_overflow_rejected" (not (cp:plan))) (cp:put 'nrows qa:nrows) (cp:plan)
(setq qa:nested 0 qa:xt 0 qa:cross 0 qa:only T qa:rating T)
(vlax-for o (vla-item (vla-get-blocks cp:doc) (vla-get-name qa:root))
  (if (= (vla-get-objectname o) "AcDbBlockReference")
    (progn
      (if (wcmatch (vla-get-name o) "VPR-*,D-VPR-*") (if (wcmatch (vla-get-name o) "VPR-*") (setq qa:xt (1+ qa:xt)))
        (progn (setq qa:nested (1+ qa:nested))
          (if (= (vla-get-name o) "EKF_CM_4x11") (setq qa:cross (1+ qa:cross)))
          (if (not (member (vla-get-name o) '("AV_1P_18" "AV_3P_54" "EKF_CM_4x11"))) (setq qa:only nil))
          (foreach at (vlax-invoke o 'GetAttributes)
            (if (= (vla-get-tagstring at) "IN_A")
              (if (/= (vla-get-textstring at) (if (= (vla-get-name o) "AV_3P_54") "16" "10")) (setq qa:rating nil)))))))))
(qa:check "19_qf_23_xt_1_cross_no_cabinet" (and qa:only (= qa:nested 20) (= qa:xt 23) (= qa:cross 1)))
(qa:check "threephase_terminal_set" (equal (mapcar '(lambda (d) (nth 7 d)) (cadr (car cp:terminalgroups))) '("VPR-2.5-GY" "VPR-2.5-GY" "VPR-2.5-GY" "VPR-2.5-BU" "VPR-2.5-PE-YG")))
(qa:check "singlephase_one_multilevel_terminal" (and (= (length (cdr cp:terminalgroups)) 18) (vl-every '(lambda (group) (and (= (length (cadr group)) 1) (= (nth 7 (car (cadr group))) "VPR-2.5-3L-GY"))) (cdr cp:terminalgroups))))
(qa:check "section_endcaps" (and (= (length cp:caps) 2) (member "D-VPR-2.5" (mapcar '(lambda (d) (nth 7 d)) cp:caps)) (member "D-VPR-2.5-3L" (mapcar '(lambda (d) (nth 7 d)) cp:caps))))
(qa:check "cross_connections" (equal cp:cross-counts '(8 6 7 0)))
(qa:check "ratings_from_excel" qa:rating)
(setq qa:stage "dialogs" qid (load_dialog "C:/Users/user/Desktop/02_Справочники_CAD_Revit/odnolineyka/2_AutoCAD/Компоновка/SX_Panel.dcl"))
(qa:check "dialog_main" (new_dialog "cp_main" qid))
(set_tile "gap" "60") (qa:check "dialog_gap" (= (get_tile "gap") "60"))
(done_dialog 0)
(qa:check "dialog_mappings" (new_dialog "cp_sizes" qid))
(done_dialog 0) (unload_dialog qid)
(setq qa:stage "dynamic" qa:states (cp:states "SX_DYN_MCB"))
(qa:check "dynamic_states" (> (length qa:states) 1))
(setq qa:bb (cp:measure "SX_DYN_MCB" 1.0 0.0 (cadr qa:states)))
(qa:check "dynamic_measurement" (and (> (- (nth 2 qa:bb) (nth 0 qa:bb)) 0.0) (> (- (nth 3 qa:bb) (nth 1 qa:bb)) 0.0)))
(cp:lib-close)
(setq qa:stage "update" qa:oldname (vla-get-name qa:root))
(vla-put-insertionpoint qa:root (vlax-3d-point '(10.0 20.0 0.0)))
(vla-put-rotation qa:root 0.2) (vla-put-xscalefactor qa:root 1.25) (vla-put-yscalefactor qa:root 1.25)
(defun cp:pick () (list qa:root (vlax-ldata-get qa:root "settings")))
(cp:run T nil)
(setq qa:new (vla-item (vla-get-modelspace cp:doc) 0))
(qa:check "update_single_root" (= (vla-get-count (vla-get-modelspace cp:doc)) 1))
(qa:check "update_replaced" (/= qa:oldname (vla-get-name qa:new)))
(qa:check "update_preserves_transform"
  (and (equal (vla-get-rotation qa:new) 0.2 0.00001)
       (equal (vla-get-xscalefactor qa:new) 1.25 0.00001)
       (equal (vlax-safearray->list (vlax-variant-value (vla-get-insertionpoint qa:new))) '(10.0 20.0 0.0) 0.00001)))
(qa:check "saved_settings" (= (cdr (assoc 'panel (vlax-ldata-get qa:new "settings"))) (cp:g 'panel)))
(vla-put-insertionpoint qa:new (vlax-3d-point '(0.0 0.0 0.0)))
(vla-put-rotation qa:new 0.0) (vla-put-xscalefactor qa:new 1.0) (vla-put-yscalefactor qa:new 1.0)
(load "C:/Users/user/Desktop/02_Справочники_CAD_Revit/odnolineyka/2_AutoCAD/Компоновка/SX_Panel.lsp")
(vla-put-activelayer cp:doc (vla-item (vla-get-layers cp:doc) "0"))
(setvar "CTAB" "Model")
(vla-regen cp:doc 1)
(vla-zoomwindow (vlax-get-acad-object) (vlax-3d-point '(-25.0 -20.0 0.0)) (vlax-3d-point '(765.0 470.0 0.0)))
(vla-save cp:doc)
(close qf))) (princ)
