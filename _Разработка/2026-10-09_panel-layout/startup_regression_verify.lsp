(if (= (getvar "DWGNAME") "CPDRAW_regression.dwg")
(progn
(qa:check "cpdraw_created_one_layout" (= (vla-get-count (vla-get-modelspace cp:doc)) 1))
(setq qa:root (vla-item (vla-get-modelspace cp:doc) 0) qa:oldname (vla-get-name qa:root))
(qa:check "layout_has_saved_settings" (vlax-ldata-get qa:root "settings"))
(qa:check "library_closed_after_cpdraw" (null cp:libsrc))
(qa:check "excel_released_after_cpdraw" (null cp:wb))
(write-line (strcat "devices=" (itoa (length cp:devices)) " terminals=" (itoa (length cp:terminals))) qa:f)
(vla-put-insertionpoint qa:root (cp:p 10.0 20.0))
(vla-put-rotation qa:root 0.2) (vla-put-xscalefactor qa:root 1.25) (vla-put-yscalefactor qa:root 1.25)
(defun cp:pick () (list qa:root (vlax-ldata-get qa:root "settings")))
(c:CPUPDATE)
(setq qa:root (vla-item (vla-get-modelspace cp:doc) 0))
(qa:check "cpupdate_replaced_layout" (/= qa:oldname (vla-get-name qa:root)))
(qa:check "cpupdate_preserves_transform" (and (equal (vla-get-rotation qa:root) 0.2 0.00001) (equal (vla-get-xscalefactor qa:root) 1.25 0.00001) (equal (vlax-safearray->list (vlax-variant-value (vla-get-insertionpoint qa:root))) '(10.0 20.0 0.0) 0.00001)))
(setq qa:oldname (vla-get-name qa:root))
(defun cp:dialog () (cp:put 'slots 30) T)
(c:CPEDIT)
(setq qa:root (vla-item (vla-get-modelspace cp:doc) 0))
(qa:check "cpedit_replaced_layout" (/= qa:oldname (vla-get-name qa:root)))
(qa:check "cpedit_saves_parameters" (= (cdr (assoc 'slots (vlax-ldata-get qa:root "settings"))) 30))
(setq qa:oldname (vla-get-name qa:root))
(defun cp:dialog () (cp:fail "Controlled failure: original message"))
(c:CPDRAW)
(qa:check "controlled_failure_preserves_layout" (and (= (vla-get-count (vla-get-modelspace cp:doc)) 1) (= qa:oldname (vla-get-name qa:root))))
(qa:check "controlled_failure_closes_library_and_excel" (and (null cp:libsrc) (null cp:wb)))
(load "C:/Users/user/Desktop/02_Справочники_CAD_Revit/odnolineyka/2_AutoCAD/Компоновка/SX_Panel.lsp")
(qa:check "cpfail_exits_without_undefined_error" (= (vl-catch-all-error-message (vl-catch-all-apply 'cp:fail '("Controlled failure"))) "quit / exit abort"))
(vla-save cp:doc) (close qa:f)
)) (princ)
