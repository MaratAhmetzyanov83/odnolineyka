(setq zf (open "C:/Users/user/Desktop/02_Справочники_CAD_Revit/odnolineyka/_Разработка/2026-10-09_panel-layout/load_debug.txt" "w"))
(setq zr (vl-catch-all-apply '(lambda () (eval (read "(vl-load-com)"))) nil))
(prin1 (list 5 (if (vl-catch-all-error-p zr) (vl-catch-all-error-message zr) "OK")) zf) (write-line "" zf)
(setq zr (vl-catch-all-apply '(lambda () (eval (read "(setq cp:version \"1.0\" cp:app \"SX_PANEL\")"))) nil))
(prin1 (list 6 (if (vl-catch-all-error-p zr) (vl-catch-all-error-message zr) "OK")) zf) (write-line "" zf)
(setq zr (vl-catch-all-apply '(lambda () (eval (read "(defun cp:cp (c)\n  (if (= (getvar \"LISPSYS\") 0)\n    (cond ((and (>= c 1040) (<= c 1103)) (- c 848)) ((= c 1025) 168) ((= c 1105) 184) ((= c 8470) 185) (t c)) c))"))) nil))
(prin1 (list 9 (if (vl-catch-all-error-p zr) (vl-catch-all-error-message zr) "OK")) zf) (write-line "" zf)
(setq zr (vl-catch-all-apply '(lambda () (eval (read "(defun cp:ru (cs) (apply 'strcat (mapcar '(lambda (c) (chr (cp:cp c))) cs)))"))) nil))
(prin1 (list 12 (if (vl-catch-all-error-p zr) (vl-catch-all-error-message zr) "OK")) zf) (write-line "" zf)
(setq zr (vl-catch-all-apply '(lambda () (eval (read "(defun cp:v (v)\n  (cond ((= (type v) 'VARIANT) (if (member (vlax-variant-type v) '(0 1 10)) nil (cp:v (vlax-variant-value v))))\n        ((and (= (type v) 'STR) (= v \"\")) nil) (t v)))"))) nil))
(prin1 (list 13 (if (vl-catch-all-error-p zr) (vl-catch-all-error-message zr) "OK")) zf) (write-line "" zf)
(setq zr (vl-catch-all-apply '(lambda () (eval (read "(defun cp:s (v)\n  (cond ((null v) \"\") ((= (type v) 'STR) v) ((numberp v) (rtos v 2 2)) (t \"\")))"))) nil))
(prin1 (list 16 (if (vl-catch-all-error-p zr) (vl-catch-all-error-message zr) "OK")) zf) (write-line "" zf)
(setq zr (vl-catch-all-apply '(lambda () (eval (read "(defun cp:num (s) (distof (vl-string-translate \",\" \".\" s) 2))"))) nil))
(prin1 (list 18 (if (vl-catch-all-error-p zr) (vl-catch-all-error-message zr) "OK")) zf) (write-line "" zf)
(setq zr (vl-catch-all-apply '(lambda () (eval (read "(defun cp:norm (s) (strcase (vl-string-trim \" \" (cp:s s))))"))) nil))
(prin1 (list 19 (if (vl-catch-all-error-p zr) (vl-catch-all-error-message zr) "OK")) zf) (write-line "" zf)
(setq zr (vl-catch-all-apply '(lambda () (eval (read "(defun cp:g (key) (cdr (assoc key cp:cfg)))"))) nil))
(prin1 (list 20 (if (vl-catch-all-error-p zr) (vl-catch-all-error-message zr) "OK")) zf) (write-line "" zf)
(setq zr (vl-catch-all-apply '(lambda () (eval (read "(defun cp:put (key val)\n  (if (assoc key cp:cfg) (setq cp:cfg (subst (cons key val) (assoc key cp:cfg) cp:cfg))\n    (setq cp:cfg (cons (cons key val) cp:cfg))))"))) nil))
(prin1 (list 21 (if (vl-catch-all-error-p zr) (vl-catch-all-error-message zr) "OK")) zf) (write-line "" zf)
(setq zr (vl-catch-all-apply '(lambda () (eval (read "(defun cp:rel (o) (if (= (type o) 'VLA-OBJECT) (vl-catch-all-apply 'vlax-release-object (list o))))"))) nil))
(prin1 (list 24 (if (vl-catch-all-error-p zr) (vl-catch-all-error-message zr) "OK")) zf) (write-line "" zf)
(setq zr (vl-catch-all-apply '(lambda () (eval (read "(defun cp:close-book ()\n  (if (and cp:wb cp:opened) (vl-catch-all-apply 'vlax-invoke-method (list cp:wb 'Close :vlax-false)))\n  (cp:rel cp:wb)\n  (if (and cp:xl cp:created) (vl-catch-all-apply 'vlax-invoke-method (list cp:xl 'Quit)))\n  (cp:rel cp:xl)\n  (setq cp:wb nil cp:xl nil cp:opened nil cp:created nil))"))) nil))
(prin1 (list 25 (if (vl-catch-all-error-p zr) (vl-catch-all-error-message zr) "OK")) zf) (write-line "" zf)
(setq zr (vl-catch-all-apply '(lambda () (eval (read "(defun cp:open-book (path / wbs w)\n  (cp:close-book)\n  (setq cp:xl (vl-catch-all-apply 'vlax-get-object '(\"Excel.Application\")))\n  (if (vl-catch-all-error-p cp:xl) (setq cp:xl (vlax-create-object \"Excel.Application\") cp:created T))\n  (setq wbs (vlax-get-property cp:xl 'Workbooks))\n  (vlax-for w wbs\n    (if (and (null cp:wb) (= (strcase path) (strcase (vlax-get-property w 'FullName))))\n      (setq cp:wb w) (cp:rel w)))\n  (if (null cp:wb)\n    (setq cp:wb (vlax-invoke-method wbs 'Open path :vlax-false :vlax-true) cp:opened T))\n  (cp:rel wbs)\n  cp:wb)"))) nil))
(prin1 (list 31 (if (vl-catch-all-error-p zr) (vl-catch-all-error-message zr) "OK")) zf) (write-line "" zf)
(setq zr (vl-catch-all-apply '(lambda () (eval (read "(defun cp:range (sheet addr / shs sh rg vals)\n  (setq shs (vlax-get-property cp:wb 'Worksheets))\n  (setq sh (vl-catch-all-apply 'vlax-get-property (list shs 'Item sheet)))\n  (cp:rel shs)\n  (if (vl-catch-all-error-p sh) (error (strcat (cp:ru '(1053 1077 1090 32 1083 1080 1089 1090 1072 32 69 120 99 101 108 58 32)) sheet)))\n  (setq rg (vlax-get-property sh 'Range addr))\n  (setq vals (vl-catch-all-apply '(lambda () (vlax-safearray->list (vlax-variant-value (vlax-get-property rg 'Value2)))) nil))\n  (cp:rel rg) (cp:rel sh)\n  (if (vl-catch-all-error-p vals) (error (vl-catch-all-error-message vals)))\n  (mapcar '(lambda (r) (mapcar 'cp:v r)) vals))"))) nil))
(prin1 (list 43 (if (vl-catch-all-error-p zr) (vl-catch-all-error-message zr) "OK")) zf) (write-line "" zf)
(setq zr (vl-catch-all-apply '(lambda () (eval (read "(defun cp:read-book (path /)\n  (cp:open-book path)\n  (setq cp:rows (cp:range (cp:ru '(1054 1076 1085 1086 1083 1080 1085 1077 1081 1082 1072)) \"A3:BY1000\")\n        cp:catalog (cp:range (cp:ru '(1050 1072 1090 1072 1083 1086 1075)) \"A4:P1000\") cp:panels nil)\n  (foreach r cp:rows (if (and (car r) (not (member (cp:s (car r)) cp:panels))) (setq cp:panels (append cp:panels (list (cp:s (car r)))))))\n  (cp:close-book))"))) nil))
(prin1 (list 53 (if (vl-catch-all-error-p zr) (vl-catch-all-error-message zr) "OK")) zf) (write-line "" zf)
(setq zr (vl-catch-all-apply '(lambda () (eval (read "(defun cp:at (r c) (nth (1- c) r))"))) nil))
(prin1 (list 61 (if (vl-catch-all-error-p zr) (vl-catch-all-error-message zr) "OK")) zf) (write-line "" zf)
(setq zr (vl-catch-all-apply '(lambda () (eval (read "(defun cp:words (s / i ch word res)\n  (setq i 1 word \"\")\n  (while (<= i (strlen s))\n    (setq ch (substr s i 1))\n    (if (= ch \" \") (progn (if (/= word \"\") (setq res (cons word res))) (setq word \"\")) (setq word (strcat word ch)))\n    (setq i (1+ i)))\n  (if (/= word \"\") (setq res (cons word res))) (reverse res))"))) nil))
(prin1 (list 62 (if (vl-catch-all-error-p zr) (vl-catch-all-error-message zr) "OK")) zf) (write-line "" zf)
(setq zr (vl-catch-all-apply '(lambda () (eval (read "(defun cp:qparts (s / toks poles amp diff tk)\n  (setq toks (cp:words (cp:s s)) poles \"\" amp nil diff nil)\n  (foreach tk toks\n    (cond ((wcmatch (strcase tk) \"#P\") (setq poles (strcase tk)))\n          ((wcmatch (strcase tk) \"*30*\") (setq diff T))\n          ((null amp) (setq amp (cp:num (vl-string-left-trim \"ABCDabcd\" tk))))))\n  ;; distof не принимает букву А на конце; взять ведущую числовую часть.\n  (if (null amp)\n    (foreach tk toks\n      (if (and (null amp) (wcmatch (strcase tk) \"[BCD]#*\")) (setq amp (atof (substr tk 2))))))\n  (list poles amp diff))"))) nil))
(prin1 (list 69 (if (vl-catch-all-error-p zr) (vl-catch-all-error-message zr) "OK")) zf) (write-line "" zf)
(setq zr (vl-catch-all-apply '(lambda () (eval (read "(defun cp:qcatalog (r / parts c candidates diff qchar model)\n  (setq parts (cp:qparts (cp:at r 8)) candidates nil)\n  (foreach c cp:catalog\n    (setq diff (= (cp:norm (nth 10 c)) (cp:norm (cp:ru '(1076 1072)))))\n    (if (and (member (cp:norm (car c)) (list (cp:norm (cp:ru '(1040 1074 1090 1086 1084 1072 1090))) (cp:norm (cp:ru '(1044 1080 1092 1072 1074 1090 1086 1084 1072 1090)))))\n             (= (cp:norm (nth 8 c)) (car parts))\n             (numberp (nth 9 c)) (numberp (cadr parts)) (equal (nth 9 c) (cadr parts) 0.001)\n             (equal diff (caddr parts)))\n      (setq candidates (cons c candidates))))\n  ;; При нескольких моделях не угадывать производителя/серию.\n  (if (= (length candidates) 1) (car candidates)))"))) nil))
(prin1 (list 80 (if (vl-catch-all-error-p zr) (vl-catch-all-error-message zr) "OK")) zf) (write-line "" zf)
(setq zr (vl-catch-all-apply '(lambda () (eval (read "(defun cp:model-catalog (model / matches)\n  (foreach c cp:catalog (if (= (cp:norm (nth 2 c)) (cp:norm model)) (setq matches (cons c matches))))\n  (if (= (length matches) 1) (car matches)))"))) nil))
(prin1 (list 91 (if (vl-catch-all-error-p zr) (vl-catch-all-error-message zr) "OK")) zf) (write-line "" zf)
(setq zr (vl-catch-all-apply '(lambda () (eval (read "(defun cp:add-device (id model cat kind row / key mods)\n  (setq key (strcat kind \"|\" (cp:norm model)) mods (if cat (nth 11 cat)))\n  (if (or (not (numberp mods)) (<= mods 0)) (setq mods nil))\n  (setq cp:devices (append cp:devices (list (list id key model mods (cp:g 'devh) kind row)))))"))) nil))
(prin1 (list 94 (if (vl-catch-all-error-p zr) (vl-catch-all-error-message zr) "OK")) zf) (write-line "" zf)
(setq zr (vl-catch-all-apply '(lambda () (eval (read "(defun cp:collect (panel / selected r idx cat qid mid model n typ txt id seenq seenm seenxt k counts)\n  (setq cp:devices nil cp:terminals nil selected nil idx 3 counts nil)\n  (foreach r cp:rows\n    (if (and (= (cp:s (car r)) panel) (numberp (cp:at r 2)) (= (cp:at r 56) 1))\n      (setq selected (cons (list r idx) selected)))\n    (setq idx (1+ idx)))\n  (setq selected (vl-sort selected '(lambda (a b) (< (cp:at (car a) 2) (cp:at (car b) 2)))))\n  (foreach rec selected\n    (setq r (car rec) idx (cadr rec) qid (cp:s (cp:at r 36)))\n    (if (and (/= qid \"\") (not (member qid seenq)))\n      (progn\n        (setq seenq (cons qid seenq) cat (cp:qcatalog r)\n              model (if cat (cp:s (nth 2 cat)) (cp:s (cp:at r 8))))\n        (cp:add-device qid model cat \"QF\" idx)\n        (setq k 0)\n        (repeat 3\n          (setq typ (cp:s (cp:at r (+ 60 k))) txt (cp:s (cp:at r (+ 9 k))))\n          (if (/= typ \"\")\n            (progn\n              (setq n (1+ (if (assoc typ counts) (cdr (assoc typ counts)) 0)))\n              (if (assoc typ counts) (setq counts (subst (cons typ n) (assoc typ counts) counts)) (setq counts (cons (cons typ n) counts)))\n              (setq id (strcat typ (itoa n)) cat (cp:model-catalog txt))\n              (cp:add-device id txt cat typ idx)))\n          (setq k (1+ k)))))\n    (setq mid (cp:s (cp:at r 34)) model (cp:s (cp:at r 35)))\n    (if (and (/= mid \"\") (/= model \"\") (not (member mid seenm)))\n      (progn (setq seenm (cons mid seenm)) (cp:add-device mid model (cp:model-catalog model) \"MODULE\" idx)))\n    (setq txt (cp:s (cp:at r 16)))\n    (if (and (= (cp:at r 51) 1) (/= txt \"\") (not (member txt seenxt)))\n      (progn (setq seenxt (cons txt seenxt)) (setq cp:terminals (append cp:terminals (list txt))))))\n  cp:devices)"))) nil))
(prin1 (list 98 (if (vl-catch-all-error-p zr) (vl-catch-all-error-message zr) "OK")) zf) (write-line "" zf)
(setq zr (vl-catch-all-apply '(lambda () (eval (read "(defun cp:apply-sizes ( / mapping metrics name scale rot)\n  (setq cp:devices (mapcar '(lambda (d)\n    (setq mapping (cdr (assoc (nth 1 d) (cp:g 'sizes))))\n    (if mapping\n      (progn\n        (setq name (car mapping) scale (cadr mapping) rot (caddr mapping)\n              metrics (cp:measure name scale rot (nth 3 mapping)))\n        (list (nth 0 d) (nth 1 d) (nth 2 d)\n              (/ (- (nth 2 metrics) (nth 0 metrics)) (cp:g 'pitch))\n              (- (nth 3 metrics) (nth 1 metrics)) (nth 5 d) (nth 6 d) name scale rot (nth 3 mapping)))\n      d)) cp:devices)))"))) nil))
(prin1 (list 129 (if (vl-catch-all-error-p zr) (vl-catch-all-error-message zr) "OK")) zf) (write-line "" zf)
(setq zr (vl-catch-all-apply '(lambda () (eval (read "(defun cp:pack (devices capacity pitch / row x placed bad d width)\n  (setq row 0 x 0.0)\n  (foreach d devices\n    (if (not (numberp (nth 3 d))) (setq bad (strcat (cp:ru '(1053 1077 32 1079 1072 1076 1072 1085 1072 32 1096 1080 1088 1080 1085 1072 58 32)) (car d)))\n      (progn\n        (setq width (* (nth 3 d) pitch))\n        (if (> width (+ capacity 0.001)) (setq bad (strcat (cp:ru '(1040 1087 1087 1072 1088 1072 1090 32 1096 1080 1088 1077 32 1076 1086 1089 1090 1091 1087 1085 1086 1075 1086 32 1084 1077 1089 1090 1072 32 1085 1072 32 1088 1077 1081 1082 1077 58 32)) (car d)))\n          (progn\n            (if (> (+ x width) (+ capacity 0.001)) (setq row (1+ row) x 0.0))\n            (setq placed (cons (list d row x) placed) x (+ x width)))))))\n  (list (reverse placed) (if devices (1+ row) 0) bad))"))) nil))
(prin1 (list 143 (if (vl-catch-all-error-p zr) (vl-catch-all-error-message zr) "OK")) zf) (write-line "" zf)
(setq zr (vl-catch-all-apply '(lambda () (eval (read "(defun cp:plan ( / rw usable packed xtcap xtrows n maxh minpitch required pitch rsize xsize ns ps)\n  (setq cp:problem nil cp:positions nil)\n  (setq rsize (cp:role-size \"@DIN\") xsize (cp:role-size \"@XT\"))\n  (cp:put 'xtw (car xsize)) (cp:put 'xth (cadr xsize))\n  (setq cp:barw 0.0 cp:barh 0.0)\n  (if (cp:g 'bars)\n    (progn\n      (setq ns (cp:role-size \"@N\") ps (cp:role-size \"@PE\")\n            cp:barw (+ (max (car ns) (car ps)) 20.0)\n            cp:barh (+ (cadr ns) (cadr ps) 10.0)\n            cp:barN (+ (/ (cadr ps) 2.0) 5.0) cp:barPE (- (+ (/ (cadr ns) 2.0) 5.0)))))\n  (setq cp:railw (* (cp:g 'slots) (cp:g 'pitch))\n        usable (* cp:railw (- 1.0 (/ (cp:g 'reserve) 100.0))))\n  (setq cp:dinsegments (max 1 (fix (+ (/ cp:railw (car rsize)) 0.999999))) cp:dinwidth (* cp:dinsegments (car rsize)))\n  (cond\n    ((> (+ cp:dinwidth (* 2 (cp:g 'margin))) (cp:g 'w)) (setq cp:problem (strcat (cp:ru '(1053 1077 1076 1086 1089 1090 1072 1090 1086 1095 1085 1072 32 1096 1080 1088 1080 1085 1072 32 1082 1086 1088 1087 1091 1089 1072 46 32 1053 1091 1078 1085 1086 32 1085 1077 32 1084 1077 1085 1077 1077 32)) (cp:s (+ cp:dinwidth (* 2 (cp:g 'margin)))) (cp:ru '(32 1084 1084 46)))))\n    (t\n      (setq packed (cp:pack cp:devices usable (cp:g 'pitch)))\n      (cond ((caddr packed) (setq cp:problem (caddr packed)))\n            ((> (cadr packed) (cp:g 'nrows)) (setq cp:problem (strcat (cp:ru '(1053 1091 1078 1085 1086 32 1088 1077 1077 1082 32 1076 1083 1103 32 1072 1087 1087 1072 1088 1072 1090 1086 1074 58 32)) (itoa (cadr packed)) (cp:ru '(46 32 1047 1072 1076 1072 1085 1086 58 32)) (itoa (cp:g 'nrows)) \".\")))\n            (t (setq cp:positions (car packed))))))\n  (setq xtcap (fix (/ (- cp:railw cp:barw) (cp:g 'xtw))))\n  (if (and cp:terminals (<= xtcap 0)) (setq cp:problem (cp:ru '(1053 1077 1090 32 1084 1077 1089 1090 1072 32 1076 1083 1103 32 1082 1083 1077 1084 1084 58 32 1091 1084 1077 1085 1100 1096 1080 1090 1077 32 1086 1090 1089 1090 1091 1087 32 1076 1083 1103 32 1096 1080 1085 32 78 47 80 69 32 1080 1083 1080 32 1091 1074 1077 1083 1080 1095 1100 1090 1077 32 1088 1077 1081 1082 1091 46))))\n  (setq cp:xtcap xtcap cp:xtrows (if cp:terminals (1+ (fix (/ (1- (length cp:terminals)) (max 1 xtcap)))) (if (cp:g 'bars) 1 0))\n        cp:totalrows (+ (cp:g 'nrows) cp:xtrows)\n        maxh (apply 'max (append (list (cp:g 'devh) cp:barh) (if (> cp:xtrows 0) (list (cp:g 'xth))) (mapcar '(lambda (d) (nth 4 d)) cp:devices)))\n        minpitch (+ maxh (cp:g 'duct) 20.0)\n        required (+ (* 2 (cp:g 'margin)) maxh (* (1- cp:totalrows) minpitch)))\n  (if (> required (cp:g 'h)) (setq cp:problem (strcat (cp:ru '(1053 1077 1076 1086 1089 1090 1072 1090 1086 1095 1085 1072 32 1074 1099 1089 1086 1090 1072 32 1082 1086 1088 1087 1091 1089 1072 46 32 1044 1083 1103 32 1088 1077 1077 1082 32 1080 32 1082 1072 1073 1077 1083 1100 45 1082 1072 1085 1072 1083 1086 1074 32 1085 1091 1078 1085 1086 32 1085 1077 32 1084 1077 1085 1077 1077 32)) (cp:s required) (cp:ru '(32 1084 1084 46)))))\n  (setq cp:rowtop (- (cp:g 'h) (cp:g 'margin) (/ maxh 2.0))\n        cp:rowpitch (if (> cp:totalrows 1) (/ (- (cp:g 'h) (* 2 (cp:g 'margin)) maxh) (1- cp:totalrows)) 0.0))\n  (null cp:problem))"))) nil))
(prin1 (list 154 (if (vl-catch-all-error-p zr) (vl-catch-all-error-message zr) "OK")) zf) (write-line "" zf)
(setq zr (vl-catch-all-apply '(lambda () (eval (read "(defun cp:defaults ( / cfg last)\n  (setq cfg '((w . 600.0) (h . 800.0) (depth . 200.0) (nrows . 3) (slots . 24)\n              (pitch . 18.0) (reserve . 20.0) (margin . 40.0) (duct . 30.0)\n              (devh . 90.0) (xtw . 5.2) (xth . 103.0) (bars . T)))\n  (if (setq last (vlax-ldata-get \"SX_PANEL\" \"last\")) (setq cfg last))\n  (if (null (assoc 'caseblock cfg)) (setq cfg (cons (cons 'caseblock \"DKC_CQEN_1600x600x600_FRAME\") cfg)))\n  (if (null (assoc 'library cfg)) (setq cfg (cons (cons 'library (cp:default-library)) cfg)))\n  (if (null (assoc 'path cfg)) (setq cfg (cons (cons 'path (getenv \"SX_LastXls\")) cfg)))\n  (if (null (assoc 'panel cfg)) (setq cfg (cons (cons 'panel (getenv \"SX_LastPanel\")) cfg)))\n  cfg)"))) nil))
(prin1 (list 188 (if (vl-catch-all-error-p zr) (vl-catch-all-error-message zr) "OK")) zf) (write-line "" zf)
(setq zr (vl-catch-all-apply '(lambda () (eval (read "(defun cp:cfg-save ( / key val good)\n  (setq good T)\n  (foreach key '(w h depth nrows slots pitch reserve margin duct devh xtw xth)\n    (setq val (cp:num (get_tile (strcase (vl-symbol-name key) T))))\n    (if (or (null val) (if (= key 'reserve) (or (< val 0) (>= val 100)) (<= val 0))\n            (and (member key '(nrows slots)) (not (equal val (fix val) 0.000001))))\n      (setq good nil)\n      (cp:put key (if (member key '(nrows slots)) (fix val) val))))\n  (if good\n    (progn (cp:put 'library (get_tile \"library\")) (cp:put 'panel (nth (atoi (get_tile \"panel\")) cp:panels)) (cp:put 'bars (= (get_tile \"bars\") \"1\")) (done_dialog 1))\n    (set_tile \"status\" (cp:ru '(1055 1088 1086 1074 1077 1088 1100 1090 1077 32 1088 1072 1079 1084 1077 1088 1099 32 1080 32 1094 1077 1083 1086 1077 32 1082 1086 1083 1080 1095 1077 1089 1090 1074 1086 32 1088 1077 1077 1082 47 1084 1086 1076 1091 1083 1077 1081 46 32 1056 1077 1079 1077 1088 1074 58 32 48 8211 57 57 32 37 46)))))"))) nil))
(prin1 (list 198 (if (vl-catch-all-error-p zr) (vl-catch-all-error-message zr) "OK")) zf) (write-line "" zf)
(setq zr (vl-catch-all-apply '(lambda () (eval (read "(defun cp:dialog ( / id res key path)\n  (if (null (setq path (findfile \"SX_Panel.dcl\"))) (error (cp:ru '(1053 1077 32 1085 1072 1081 1076 1077 1085 32 83 88 95 80 97 110 101 108 46 100 99 108 46 32 1044 1086 1073 1072 1074 1100 1090 1077 32 1087 1072 1087 1082 1091 32 1050 1086 1084 1087 1086 1085 1086 1074 1082 1072 32 1074 32 1087 1091 1090 1080 32 1074 1089 1087 1086 1084 1086 1075 1072 1090 1077 1083 1100 1085 1099 1093 32 1092 1072 1081 1083 1086 1074 32 65 117 116 111 67 65 68 46))))\n  (setq id (load_dialog path) res 2)\n  (while (= res 2)\n    (if (not (new_dialog \"cp_main\" id)) (error (cp:ru '(1053 1077 32 1091 1076 1072 1083 1086 1089 1100 32 1086 1090 1082 1088 1099 1090 1100 32 1086 1082 1085 1086 32 1082 1086 1084 1087 1086 1085 1086 1074 1082 1080 46))))\n    (set_tile \"file\" (cp:s (cp:g 'path)))\n    (set_tile \"library\" (cp:s (cp:g 'library)))\n    (start_list \"caseblock\") (mapcar 'add_list cp:casenames) (end_list)\n    (set_tile \"caseblock\" (itoa (if (member (cp:g 'caseblock) cp:casenames) (vl-position (cp:g 'caseblock) cp:casenames) 0)))\n    (start_list \"panel\") (mapcar 'add_list cp:panels) (end_list)\n    (set_tile \"panel\" (itoa (if (member (cp:g 'panel) cp:panels) (vl-position (cp:g 'panel) cp:panels) 0)))\n    (foreach key '(w h depth nrows slots pitch reserve margin duct devh xtw xth)\n      (set_tile (strcase (vl-symbol-name key) T) (cp:s (cp:g key))))\n    (set_tile \"bars\" (if (cp:g 'bars) \"1\" \"0\"))\n    (cp:case-choice (get_tile \"caseblock\"))\n    (action_tile \"caseblock\" \"(cp:case-choice $value)\")\n    (action_tile \"browse\" \"(done_dialog 2)\")\n    (action_tile \"accept\" \"(cp:cfg-save)\") (action_tile \"cancel\" \"(done_dialog 0)\")\n    (setq res (start_dialog))\n    (if (= res 2)\n      (if (setq path (getfiled (cp:ru '(69 120 99 101 108 32 1089 32 1086 1076 1085 1086 1083 1080 1085 1077 1081 1082 1086 1081)) (cp:g 'path) \"xlsx;xlsm;xls\" 0))\n        (progn (cp:put 'path path) (cp:read-book path)))))\n  (unload_dialog id)\n  (= res 1))"))) nil))
(prin1 (list 209 (if (vl-catch-all-error-p zr) (vl-catch-all-error-message zr) "OK")) zf) (write-line "" zf)
(setq zr (vl-catch-all-apply '(lambda () (eval (read "(defun cp:size-fill ( / item size name)\n  (setq item (nth cp:size-i cp:size-items) size (cdr (assoc (car item) cp:size-data)) name (car size))\n  (set_tile \"model\" (cadr item))\n  (set_tile \"block\" (itoa (if (member name cp:blocknames) (vl-position name cp:blocknames) 0)))\n  (set_tile \"scale\" (cp:s (if (cadr size) (cadr size) 1.0)))\n  (set_tile \"rotation\" (cp:s (if (caddr size) (caddr size) 0.0)))\n  (cp:state-list (if name name \"\") (nth 3 size)))"))) nil))
(prin1 (list 233 (if (vl-catch-all-error-p zr) (vl-catch-all-error-message zr) "OK")) zf) (write-line "" zf)
(setq zr (vl-catch-all-apply '(lambda () (eval (read "(defun cp:size-store ( / key name scale rot size state)\n  (setq key (car (nth cp:size-i cp:size-items)) name (nth (atoi (get_tile \"block\")) cp:blocknames)\n        scale (cp:num (get_tile \"scale\")) rot (cp:num (get_tile \"rotation\")))\n  (if (and name (/= name \"\") scale (> scale 0) rot)\n    (progn\n      (setq state (nth (atoi (get_tile \"state\")) cp:state-options) size (cons key (list name scale rot state)))\n      (setq cp:size-data (if (assoc key cp:size-data) (subst size (assoc key cp:size-data) cp:size-data) (cons size cp:size-data))) T)\n    (progn (set_tile \"status\" (cp:ru '(1042 1099 1073 1077 1088 1080 1090 1077 32 1074 1072 1096 32 1073 1083 1086 1082 44 32 1087 1086 1083 1086 1078 1080 1090 1077 1083 1100 1085 1099 1081 32 1084 1072 1089 1096 1090 1072 1073 32 1080 32 1091 1075 1086 1083 32 1087 1086 1074 1086 1088 1086 1090 1072 46))) nil)))"))) nil))
(prin1 (list 240 (if (vl-catch-all-error-p zr) (vl-catch-all-error-message zr) "OK")) zf) (write-line "" zf)
(setq zr (vl-catch-all-apply '(lambda () (eval (read "(defun cp:size-select (new)\n  (if (cp:size-store) (progn (setq cp:size-i (atoi new)) (cp:size-fill))\n    (set_tile \"items\" (itoa cp:size-i))))"))) nil))
(prin1 (list 248 (if (vl-catch-all-error-p zr) (vl-catch-all-error-message zr) "OK")) zf) (write-line "" zf)
(setq zr (vl-catch-all-apply '(lambda () (eval (read "(defun cp:size-accept ()\n  (if (cp:size-store)\n    (if (vl-some '(lambda (p) (or (null (cadr p)) (= (cadr p) \"\"))) cp:size-data)\n      (set_tile \"status\" (cp:ru '(1053 1072 1079 1085 1072 1095 1100 1090 1077 32 1074 1072 1096 32 1073 1083 1086 1082 32 1082 1072 1078 1076 1086 1081 32 1087 1086 1079 1080 1094 1080 1080 46 32 1055 1091 1089 1090 1099 1077 32 1087 1086 1079 1080 1094 1080 1080 32 1086 1090 1084 1077 1095 1077 1085 1099 32 1079 1085 1072 1082 1086 1084 32 63 46)) )\n      (done_dialog 1))))"))) nil))
(prin1 (list 251 (if (vl-catch-all-error-p zr) (vl-catch-all-error-message zr) "OK")) zf) (write-line "" zf)
(setq zr (vl-catch-all-apply '(lambda () (eval (read "(defun cp:sizes-dialog ( / id res key d size name label)\n  (setq cp:size-items nil cp:size-data nil cp:size-i 0)\n  (foreach d cp:devices\n    (setq key (nth 1 d) size (cdr (assoc key (cp:g 'sizes))))\n    (if (null size) (setq size (list (cp:default-block d) 1.0 0.0)))\n    (if (not (assoc key cp:size-items))\n      (progn\n        (setq label (strcat (if (car size) \"\" \"? \") (car d) (cp:ru '(32 8212 32)) (nth 2 d)))\n        (setq cp:size-items (append cp:size-items (list (list key label))))\n        (setq cp:size-data (cons (cons key size) cp:size-data)))))\n  ;; Рейки, клеммы, шины и кабель-каналы используют ту же привязку к вашим блокам.\n  (foreach p '((\"@DIN\" (cp:ru '(68 73 78 45 1088 1077 1081 1082 1072)) \"DIN_TH35_L500\" 1.0 0.0)\n               (\"@XT\" (cp:ru '(1050 1083 1077 1084 1084 1072)) \"VPR-2.5-3L-GY\" 1.0 0.0)\n               (\"@N\" (cp:ru '(1050 1083 1077 1084 1084 1085 1099 1081 32 1073 1083 1086 1082 32 78)) \"EKF_CM_2x7\" 1.0 0.0)\n               (\"@PE\" (cp:ru '(1050 1083 1077 1084 1084 1085 1099 1081 32 1073 1083 1086 1082 32 80 69)) \"EKF_CM_2x7\" 1.0 0.0))\n    (setq key (car p) size (cdr (assoc key (cp:g 'sizes))))\n    (if (null size) (setq size (cddr p)))\n    (setq cp:size-items (append cp:size-items (list (list key (cadr p))))\n          cp:size-data (cons (cons key size) cp:size-data)))\n  (setq id (load_dialog (findfile \"SX_Panel.dcl\")))\n  (new_dialog \"cp_sizes\" id)\n  (start_list \"items\") (mapcar '(lambda (p) (add_list (cadr p))) cp:size-items) (end_list)\n  (start_list \"block\") (mapcar 'add_list cp:blocknames) (end_list)\n  (set_tile \"items\" \"0\") (cp:size-fill)\n  (action_tile \"items\" \"(cp:size-select $value)\")\n  (action_tile \"block\" \"(cp:block-choice $value)\")\n  (action_tile \"apply\" \"(cp:size-store)\")\n  (action_tile \"accept\" \"(cp:size-accept)\") (action_tile \"cancel\" \"(done_dialog 0)\")\n  (setq res (start_dialog)) (unload_dialog id)\n  (if (= res 1) (progn (cp:put 'sizes cp:size-data) (cp:apply-sizes) T)))"))) nil))
(prin1 (list 256 (if (vl-catch-all-error-p zr) (vl-catch-all-error-message zr) "OK")) zf) (write-line "" zf)
(setq zr (vl-catch-all-apply '(lambda () (eval (read "(defun cp:default-library ( / base)\n  (if (setq base (findfile \"SX_Panel.lsp\"))\n    (findfile (strcat (vl-filename-directory base) (cp:ru '(47 46 46 47 1041 1083 1086 1082 1080 47 83 88 95 1050 1086 1084 1087 1086 1085 1086 1074 1082 1072 95 1087 1086 1083 1100 1079 1086 1074 1072 1090 1077 1083 1100 1089 1082 1080 1077 46 100 119 103))))))"))) nil))
(prin1 (list 289 (if (vl-catch-all-error-p zr) (vl-catch-all-error-message zr) "OK")) zf) (write-line "" zf)
(setq zr (vl-catch-all-apply '(lambda () (eval (read "(defun cp:lib-close ()\n  (if cp:libdbx (cp:rel cp:libdbx))\n  (setq cp:libdbx nil cp:libsrc nil cp:libpath nil))"))) nil))
(prin1 (list 292 (if (vl-catch-all-error-p zr) (vl-catch-all-error-message zr) "OK")) zf) (write-line "" zf)
(setq zr (vl-catch-all-apply '(lambda () (eval (read "(defun cp:import-library ( / path b dest)\n  ;; Здесь читаем имена, определения копируются только по запросу cp:ensure-block.\n  (setq path (cp:g 'library) dest (vla-get-blocks cp:doc))\n  (if (and path (/= path \"\") (findfile path))\n    (progn\n      (if (not (equal cp:libpath path))\n        (progn\n          (cp:lib-close)\n          (vlax-for d (vla-get-documents (vlax-get-acad-object))\n            (if (= (strcase (vla-get-fullname d)) (strcase path)) (setq cp:libsrc d)))\n          (if (null cp:libsrc)\n            (progn\n              (setq cp:libdbx (vla-getinterfaceobject (vlax-get-acad-object) (strcat \"ObjectDBX.AxDbDocument.\" (substr (getvar \"ACADVER\") 1 2))))\n              (vla-open cp:libdbx path) (setq cp:libsrc cp:libdbx)))\n          (setq cp:libpath path)))))\n  (setq cp:blocknames (list \"\") cp:casenames nil)\n  (if cp:libsrc\n    (vlax-for b (vla-get-blocks cp:libsrc)\n      (if (and (= (vla-get-isxref b) :vlax-false) (= (vla-get-islayout b) :vlax-false)\n               (not (wcmatch (vla-get-name b) \"`**,*_G###\")))\n        (setq cp:blocknames (cons (vla-get-name b) cp:blocknames)))))\n  (vlax-for b dest\n    (if (and (not (wcmatch (vla-get-name b) \"`**,CP_*,*_G###\"))\n             (= (vla-get-isxref b) :vlax-false) (= (vla-get-islayout b) :vlax-false)\n             (not (member (vla-get-name b) cp:blocknames)))\n      (setq cp:blocknames (cons (vla-get-name b) cp:blocknames))))\n  (setq cp:blocknames (vl-sort cp:blocknames '<))\n  (foreach name cp:blocknames\n    (if (wcmatch name \"DKC_CQEN_*_FRAME\") (setq cp:casenames (append cp:casenames (list name)))))\n  (if (and (null (cp:g 'caseblock)) cp:casenames)\n    (cp:put 'caseblock (if (member \"DKC_CQEN_1600x600x600_FRAME\" cp:casenames) \"DKC_CQEN_1600x600x600_FRAME\" (car cp:casenames)))))"))) nil))
(prin1 (list 295 (if (vl-catch-all-error-p zr) (vl-catch-all-error-message zr) "OK")) zf) (write-line "" zf)
(setq zr (vl-catch-all-apply '(lambda () (eval (read "(defun cp:ensure-block (name / b arr result)\n  (if (not (tblsearch \"BLOCK\" name))\n    (progn\n      (if (null cp:libsrc) (error (strcat (cp:ru '(1053 1077 1090 32 1073 1083 1086 1082 1072 32 1074 32 1095 1077 1088 1090 1077 1078 1077 32 1080 32 1085 1077 32 1086 1090 1082 1088 1099 1090 1072 32 1073 1080 1073 1083 1080 1086 1090 1077 1082 1072 58 32)) name)))\n      (setq b (vl-catch-all-apply 'vla-item (list (vla-get-blocks cp:libsrc) name)))\n      (if (vl-catch-all-error-p b) (error (strcat (cp:ru '(1042 32 1073 1080 1073 1083 1080 1086 1090 1077 1082 1077 32 1085 1077 1090 32 1073 1083 1086 1082 1072 58 32)) name)))\n      (setq arr (vlax-make-safearray vlax-vbObject '(0 . 0))) (vlax-safearray-fill arr (list b))\n      (setq result (vl-catch-all-apply 'vla-copyobjects (list cp:libsrc arr (vla-get-blocks cp:doc))))\n      (if (vl-catch-all-error-p result) (error (vl-catch-all-error-message result))))))"))) nil))
(prin1 (list 326 (if (vl-catch-all-error-p zr) (vl-catch-all-error-message zr) "OK")) zf) (write-line "" zf)
(setq zr (vl-catch-all-apply '(lambda () (eval (read "(defun cp:set-state (ob state / prop allowed found)\n  (if (and state (/= state \"\") (= (vla-get-isdynamicblock ob) :vlax-true))\n    (progn\n      (foreach prop (vlax-invoke ob 'GetDynamicBlockProperties)\n        (setq allowed (cp:dyn-values prop))\n        (if (member state allowed)\n          (progn (vla-put-value prop (vlax-make-variant state (vlax-variant-type (vla-get-value prop)))) (setq found T))))\n      (if (null found) (error (strcat (cp:ru '(1053 1077 1090 32 1080 1089 1087 1086 1083 1085 1077 1085 1080 1103 32 1076 1080 1085 1072 1084 1080 1095 1077 1089 1082 1086 1075 1086 32 1073 1083 1086 1082 1072 58 32)) state)))))\n  (vla-update ob))"))) nil))
(prin1 (list 335 (if (vl-catch-all-error-p zr) (vl-catch-all-error-message zr) "OK")) zf) (write-line "" zf)
(setq zr (vl-catch-all-apply '(lambda () (eval (read "(defun cp:dyn-values (prop / vals)\n  (setq vals (vl-catch-all-apply 'vla-get-allowedvalues (list prop)))\n  (if (not (vl-catch-all-error-p vals))\n    (progn (setq vals (cp:v vals))\n      (if (= (type vals) 'SAFEARRAY) (vl-remove-if-not '(lambda (v) (= (type v) 'STR)) (mapcar 'cp:v (vlax-safearray->list vals)))))))"))) nil))
(prin1 (list 344 (if (vl-catch-all-error-p zr) (vl-catch-all-error-message zr) "OK")) zf) (write-line "" zf)
(setq zr (vl-catch-all-apply '(lambda () (eval (read "(defun cp:states (name / tmp ob result prop)\n  (cp:ensure-block name)\n  (setq tmp (vla-add (vla-get-blocks cp:doc) (cp:p 0.0 0.0) (strcat \"CP_STATES_\" (itoa (abs (getvar \"MILLISECS\"))))))\n  (setq ob (vla-insertblock tmp (cp:p 0.0 0.0) name 1.0 1.0 1.0 0.0))\n  (if (= (vla-get-isdynamicblock ob) :vlax-true)\n    (foreach prop (vlax-invoke ob 'GetDynamicBlockProperties) (setq result (append result (cp:dyn-values prop)))))\n  (vla-delete ob) (vla-delete tmp)\n  (cons \"\" result))"))) nil))
(prin1 (list 349 (if (vl-catch-all-error-p zr) (vl-catch-all-error-message zr) "OK")) zf) (write-line "" zf)
(setq zr (vl-catch-all-apply '(lambda () (eval (read "(defun cp:state-list (name state)\n  (setq cp:state-options (if (/= name \"\") (cp:states name) (list \"\")))\n  (start_list \"state\") (mapcar 'add_list cp:state-options) (end_list)\n  (set_tile \"state\" (itoa (if (member state cp:state-options) (vl-position state cp:state-options) 0))))"))) nil))
(prin1 (list 357 (if (vl-catch-all-error-p zr) (vl-catch-all-error-message zr) "OK")) zf) (write-line "" zf)
(setq zr (vl-catch-all-apply '(lambda () (eval (read "(defun cp:block-choice (index)\n  (cp:state-list (nth (atoi index) cp:blocknames) \"\"))"))) nil))
(prin1 (list 361 (if (vl-catch-all-error-p zr) (vl-catch-all-error-message zr) "OK")) zf) (write-line "" zf)
(setq zr (vl-catch-all-apply '(lambda () (eval (read "(defun cp:case-choice (index / name tokens dims)\n  (setq name (nth (atoi index) cp:casenames))\n  (cp:put 'caseblock name)\n  (setq tokens (cp:words (vl-string-translate \"_x\" \"  \" name)))\n  (if (= (car tokens) \"DKC\")\n    (progn (cp:put 'h (atof (nth 2 tokens))) (cp:put 'w (atof (nth 3 tokens))) (cp:put 'depth (atof (nth 4 tokens)))))\n  (foreach key '(w h depth) (set_tile (strcase (vl-symbol-name key) T) (cp:s (cp:g key)))))"))) nil))
(prin1 (list 363 (if (vl-catch-all-error-p zr) (vl-catch-all-error-message zr) "OK")) zf) (write-line "" zf)
(setq zr (vl-catch-all-apply '(lambda () (eval (read "(defun cp:default-block (d / parts name)\n  (setq name (nth 2 d))\n  (cond\n    ((member name cp:blocknames) name)\n    ((member (strcat name \"_FRONT\") cp:blocknames) (strcat name \"_FRONT\"))\n    ((= (nth 5 d) \"QF\")\n     (setq parts (cp:qparts name))\n     (cond ((and (caddr parts) (= (car parts) \"2P\")) \"DS201\")\n           ((and (caddr parts) (member (car parts) '(\"3P\" \"4P\"))) \"DA_4P_135\")\n           ((= (car parts) \"1P\") \"S201\") ((= (car parts) \"2P\") \"AV_2P_36\")\n           ((= (car parts) \"3P\") \"S203\") ((= (car parts) \"4P\") \"AV_4P_72\")))\n    ((= (nth 5 d) \"KM\") \"CT_ACDC_4P_63A_FRONT\")\n    ((= (nth 5 d) \"PS\") (if (member \"ARV-DRP480-PFC-24\" cp:blocknames) \"ARV-DRP480-PFC-24\" nil))))"))) nil))
(prin1 (list 370 (if (vl-catch-all-error-p zr) (vl-catch-all-error-message zr) "OK")) zf) (write-line "" zf)
(setq zr (vl-catch-all-apply '(lambda () (eval (read "(defun cp:measure (name scale rot state / key cached blocks tmp ob p1 p2 result)\n  (setq key (list name scale rot state))\n  (if (setq cached (assoc key cp:measure-cache)) (cdr cached)\n    (progn\n      (cp:ensure-block name)\n      (setq blocks (vla-get-blocks cp:doc) tmp (vla-add blocks (cp:p 0.0 0.0) (strcat \"CP_MEASURE_\" (itoa (abs (getvar \"MILLISECS\"))))))\n      (setq ob (vla-insertblock tmp (cp:p 0.0 0.0) name scale scale scale (* pi (/ rot 180.0))))\n      (cp:set-state ob state)\n      (vla-getboundingbox ob 'p1 'p2)\n      (setq p1 (vlax-safearray->list p1) p2 (vlax-safearray->list p2) result (list (car p1) (cadr p1) (car p2) (cadr p2)))\n      (vla-delete ob) (vla-delete tmp)\n      (if (or (< (- (nth 2 result) (nth 0 result)) 0.01) (< (- (nth 3 result) (nth 1 result)) 0.01)) (error (strcat (cp:ru '(1053 1077 1074 1077 1088 1085 1099 1077 32 1075 1072 1073 1072 1088 1080 1090 1099 32 1073 1083 1086 1082 1072 58 32)) name)))\n      (setq cp:measure-cache (cons (cons key result) cp:measure-cache)) result)))"))) nil))
(prin1 (list 383 (if (vl-catch-all-error-p zr) (vl-catch-all-error-message zr) "OK")) zf) (write-line "" zf)
(setq zr (vl-catch-all-apply '(lambda () (eval (read "(defun cp:mapping (key) (cdr (assoc key (cp:g 'sizes))))"))) nil))
(prin1 (list 396 (if (vl-catch-all-error-p zr) (vl-catch-all-error-message zr) "OK")) zf) (write-line "" zf)
(setq zr (vl-catch-all-apply '(lambda () (eval (read "(defun cp:role-metrics (key / m)\n  (if (setq m (cp:mapping key)) (cp:measure (car m) (cadr m) (caddr m) (nth 3 m))\n    (error (strcat (cp:ru '(1053 1077 32 1085 1072 1079 1085 1072 1095 1077 1085 32 1073 1083 1086 1082 58 32)) key))))"))) nil))
(prin1 (list 397 (if (vl-catch-all-error-p zr) (vl-catch-all-error-message zr) "OK")) zf) (write-line "" zf)
(setq zr (vl-catch-all-apply '(lambda () (eval (read "(defun cp:role-size (key / bb)\n  (setq bb (cp:role-metrics key)) (list (- (nth 2 bb) (nth 0 bb)) (- (nth 3 bb) (nth 1 bb))))"))) nil))
(prin1 (list 400 (if (vl-catch-all-error-p zr) (vl-catch-all-error-message zr) "OK")) zf) (write-line "" zf)
(setq zr (vl-catch-all-apply '(lambda () (eval (read "(defun cp:place-block (mapping x y lay id / name scale rot bb ob att)\n  (setq name (car mapping) scale (cadr mapping) rot (caddr mapping) bb (cp:measure name scale rot (nth 3 mapping)))\n  (setq ob (vla-insertblock cp:space (cp:p (- x (nth 0 bb)) (- y (/ (+ (nth 1 bb) (nth 3 bb)) 2.0))) name scale scale scale (* pi (/ rot 180.0))))\n  (cp:set-state ob (nth 3 mapping))\n  (vla-put-layer ob lay)\n  (if (and id (= (vla-get-hasattributes ob) :vlax-true))\n    (foreach att (vlax-invoke ob 'GetAttributes)\n      (if (member (strcase (vla-get-tagstring att)) (list \"ID\" \"QF\" \"XT\" \"TAG\" \"NAME\" \"1\" (strcase (cp:ru '(1050 1052))))) (vla-put-textstring att id))))\n  ob)"))) nil))
(prin1 (list 402 (if (vl-catch-all-error-p zr) (vl-catch-all-error-message zr) "OK")) zf) (write-line "" zf)
(setq zr (vl-catch-all-apply '(lambda () (eval (read "(defun cp:p (x y) (vlax-3d-point (list x y 0.0)))"))) nil))
(prin1 (list 413 (if (vl-catch-all-error-p zr) (vl-catch-all-error-message zr) "OK")) zf) (write-line "" zf)
(setq zr (vl-catch-all-apply '(lambda () (eval (read "(defun cp:layer (name color / lay)\n  (setq lay (vl-catch-all-apply 'vla-item (list (vla-get-layers cp:doc) name)))\n  (if (vl-catch-all-error-p lay) (setq lay (vla-add (vla-get-layers cp:doc) name)))\n  (vla-put-color lay color) name)"))) nil))
(prin1 (list 414 (if (vl-catch-all-error-p zr) (vl-catch-all-error-message zr) "OK")) zf) (write-line "" zf)
(setq zr (vl-catch-all-apply '(lambda () (eval (read "(defun cp:layers ()\n  (foreach p '((\"CP_CASE\" 7) (\"CP_DIN\" 8) (\"CP_DEVICES\" 7) (\"CP_TEXT\" 7) (\"CP_DUCT\" 8) (\"CP_N\" 4) (\"CP_PE\" 3) (\"CP_DIMS\" 7)) (cp:layer (car p) (cadr p))))"))) nil))
(prin1 (list 418 (if (vl-catch-all-error-p zr) (vl-catch-all-error-message zr) "OK")) zf) (write-line "" zf)
(setq zr (vl-catch-all-apply '(lambda () (eval (read "(defun cp:style ( / st)\n  (setq st (vl-catch-all-apply 'vla-item (list (vla-get-textstyles cp:doc) \"CP_GOST\")))\n  (if (vl-catch-all-error-p st) (setq st (vla-add (vla-get-textstyles cp:doc) \"CP_GOST\")))\n  (vla-setfont st \"GOST 2.304 type A\" :vlax-false :vlax-false 204 34)\n  (vla-put-height st 0.0) (vla-put-width st 1.0))"))) nil))
(prin1 (list 420 (if (vl-catch-all-error-p zr) (vl-catch-all-error-message zr) "OK")) zf) (write-line "" zf)
(setq zr (vl-catch-all-apply '(lambda () (eval (read "(defun cp:line (x1 y1 x2 y2 lay / ob)\n  (setq ob (vla-addline cp:space (cp:p x1 y1) (cp:p x2 y2))) (vla-put-layer ob lay) ob)"))) nil))
(prin1 (list 425 (if (vl-catch-all-error-p zr) (vl-catch-all-error-message zr) "OK")) zf) (write-line "" zf)
(setq zr (vl-catch-all-apply '(lambda () (eval (read "(defun cp:rect (x1 y1 x2 y2 lay / ob pts)\n  (setq pts (vlax-make-safearray vlax-vbDouble '(0 . 7)))\n  (vlax-safearray-fill pts (list x1 y1 x2 y1 x2 y2 x1 y2))\n  (setq ob (vla-addlightweightpolyline cp:space pts))\n  (vla-put-closed ob :vlax-true) (vla-put-layer ob lay) ob)"))) nil))
(prin1 (list 427 (if (vl-catch-all-error-p zr) (vl-catch-all-error-message zr) "OK")) zf) (write-line "" zf)
(setq zr (vl-catch-all-apply '(lambda () (eval (read "(defun cp:text (x y h text width lay / ob bb1 bb2 actual)\n  (setq ob (vla-addtext cp:space text (cp:p x y) h))\n  (vla-put-stylename ob \"CP_GOST\") (vla-put-layer ob lay)\n  (vla-put-alignment ob 10) (vla-put-textalignmentpoint ob (cp:p x y))\n  (vla-getboundingbox ob 'bb1 'bb2)\n  (setq actual (- (car (vlax-safearray->list bb2)) (car (vlax-safearray->list bb1))))\n  (if (and (> width 0) (> actual width)) (vla-put-scalefactor ob (/ width actual)))\n  ob)"))) nil))
(prin1 (list 432 (if (vl-catch-all-error-p zr) (vl-catch-all-error-message zr) "OK")) zf) (write-line "" zf)
(setq zr (vl-catch-all-apply '(lambda () (eval (read "(defun cp:circle (x y r lay / ob)\n  (setq ob (vla-addcircle cp:space (cp:p x y) r)) (vla-put-layer ob lay))"))) nil))
(prin1 (list 440 (if (vl-catch-all-error-p zr) (vl-catch-all-error-message zr) "OK")) zf) (write-line "" zf)
(setq zr (vl-catch-all-apply '(lambda () (eval (read "(defun cp:dim (x1 y1 x2 y2 xt yt / ob)\n  (setq ob (vla-adddimaligned cp:space (cp:p x1 y1) (cp:p x2 y2) (cp:p xt yt)))\n  (vla-put-layer ob \"CP_DIMS\") (vla-put-textheight ob 4.0) (vla-put-arrowheadsize ob 3.0)\n  (vla-put-textstyle ob \"CP_GOST\") (vla-put-linearscalefactor ob 1.0)\n  (vla-put-primaryunitsprecision ob 0) (vla-put-textoverride ob \"<>\"))"))) nil))
(prin1 (list 442 (if (vl-catch-all-error-p zr) (vl-catch-all-error-message zr) "OK")) zf) (write-line "" zf)
(setq zr (vl-catch-all-apply '(lambda () (eval (read "(defun cp:yc (row) (- cp:rowtop (* row cp:rowpitch)))"))) nil))
(prin1 (list 447 (if (vl-catch-all-error-p zr) (vl-catch-all-error-message zr) "OK")) zf) (write-line "" zf)
(setq zr (vl-catch-all-apply '(lambda () (eval (read "(defun cp:device (pos left / d x y w h)\n  (setq d (car pos) x (+ left (nth 2 pos)) y (cp:yc (cadr pos)) w (* (nth 3 d) (cp:g 'pitch)) h (nth 4 d))\n  (cp:place-block (list (nth 7 d) (nth 8 d) (nth 9 d) (nth 10 d)) x y \"CP_DEVICES\" (car d))\n  (cp:text (+ x (/ w 2.0)) (+ y (/ h 2.0) 8.0) 4.0 (car d) (- w 2.0) \"CP_TEXT\"))"))) nil))
(prin1 (list 448 (if (vl-catch-all-error-p zr) (vl-catch-all-error-message zr) "OK")) zf) (write-line "" zf)
(setq zr (vl-catch-all-apply '(lambda () (eval (read "(defun cp:draw-geometry ( / w h left right row y ducty usable pos xti x tr ty barsx yy n rsize bsize i)\n  (setq w (cp:g 'w) h (cp:g 'h) left (/ (- w cp:railw) 2.0) right (+ left cp:railw)\n        usable (* cp:railw (- 1.0 (/ (cp:g 'reserve) 100.0))) rsize (cp:role-size \"@DIN\"))\n  (setq casebb (cp:measure (cp:g 'caseblock) 1.0 0.0 nil))\n  (cp:place-block (list (cp:g 'caseblock) 1.0 0.0) 0.0 (/ (- (nth 3 casebb) (nth 1 casebb)) 2.0) \"CP_CASE\" nil)\n  (cp:text (/ w 2.0) (+ h 30.0) 8.0 (strcat (cp:ru '(1050 1086 1084 1087 1086 1085 1086 1074 1082 1072 32 1097 1080 1090 1072 32)) (cp:g 'panel)) w \"CP_TEXT\")\n  (cp:text (/ w 2.0) (+ h 12.0) 4.0 (strcat (cp:ru '(1050 1086 1088 1087 1091 1089 32)) (cp:s w) \" x \" (cp:s h) \" x \" (cp:s (cp:g 'depth)) (cp:ru '(32 1084 1084 59 32 1074 1080 1076 32 1080 1079 1085 1091 1090 1088 1080))) w \"CP_TEXT\")\n  (setq row 0)\n  (repeat cp:totalrows\n    (setq y (cp:yc row) i 0)\n    (repeat cp:dinsegments\n      (cp:place-block (cp:mapping \"@DIN\") (+ (/ (- w cp:dinwidth) 2.0) (* i (car rsize))) y \"CP_DIN\" nil)\n      (setq i (1+ i)))\n    (cp:text 29.0 y 3.5 (strcat \"DIN \" (itoa (1+ row))) 25.0 \"CP_TEXT\")\n    (if (and (< row (cp:g 'nrows)) (> (cp:g 'reserve) 0))\n      (progn (cp:rect (+ left usable) (- y 40.0) right (+ y 40.0) \"CP_DUCT\")\n             (cp:text (/ (+ left usable right) 2.0) y 4.0 (cp:ru '(1056 1077 1079 1077 1088 1074)) (- cp:railw usable 4.0) \"CP_TEXT\")))\n    (if (< row (1- cp:totalrows))\n      (progn (setq ducty (- y (/ cp:rowpitch 2.0)))\n             (cp:rect left (- ducty (/ (cp:g 'duct) 2.0)) right (+ ducty (/ (cp:g 'duct) 2.0)) \"CP_DUCT\")\n             (cp:text (/ w 2.0) ducty 3.5 (cp:ru '(1050 1072 1073 1077 1083 1100 45 1082 1072 1085 1072 1083)) (- cp:railw 10.0) \"CP_TEXT\")))\n    (setq row (1+ row)))\n  (foreach pos cp:positions (cp:device pos left))\n  (setq xti 0)\n  (foreach id cp:terminals\n    (setq tr (fix (/ xti cp:xtcap)) ty (cp:yc (+ (cp:g 'nrows) tr)) x (+ left (* (rem xti cp:xtcap) (cp:g 'xtw))))\n    (cp:place-block (cp:mapping \"@XT\") x ty \"CP_DEVICES\" id)\n    (setq ob (cp:text (+ x (/ (cp:g 'xtw) 2.0)) (+ ty (/ (cp:g 'xth) 2.0) 14.0) 2.5 id 28.0 \"CP_TEXT\"))\n    (vla-put-rotation ob (/ pi 2.0)) (setq xti (1+ xti)))\n  (if (and (cp:g 'bars) (> cp:xtrows 0))\n    (progn (setq barsx (+ (- right cp:barw) 10.0) y (cp:yc (1- cp:totalrows)))\n      (foreach p '((\"@N\" \"N\" \"CP_N\" 18.0) (\"@PE\" \"PE\" \"CP_PE\" -18.0))\n        (setq yy (+ y (if (= (car p) \"@N\") cp:barN cp:barPE)) bsize (cp:role-size (car p)))\n        (cp:place-block (cp:mapping (car p)) barsx yy (nth 2 p) (cadr p))\n        (cp:text (+ barsx (/ (car bsize) 2.0)) (+ yy (/ (cadr bsize) 2.0) 8.0) 4.0 (cadr p) (car bsize) (nth 2 p)))))\n  (cp:dim 0.0 0.0 w 0.0 (/ w 2.0) -28.0) (cp:dim 0.0 0.0 0.0 h -28.0 (/ h 2.0))\n  (cp:text (/ w 2.0) -55.0 4.0 (cp:ru '(1040 1087 1087 1072 1088 1072 1090 1099 44 32 1088 1077 1081 1082 1080 32 1080 32 1082 1083 1077 1084 1084 1099 58 32 1087 1086 1083 1100 1079 1086 1074 1072 1090 1077 1083 1100 1089 1082 1080 1077 32 1073 1083 1086 1082 1080 46 32 1052 1072 1089 1096 1090 1072 1073 32 1073 1083 1086 1082 1072 32 1089 1086 1093 1088 1072 1085 1103 1077 1090 1089 1103 46)) (+ w 50.0) \"CP_TEXT\")\n  (cp:draw-list (+ w 45.0) h))"))) nil))
(prin1 (list 452 (if (vl-catch-all-error-p zr) (vl-catch-all-error-message zr) "OK")) zf) (write-line "" zf)
(setq zr (vl-catch-all-apply '(lambda () (eval (read "(defun cp:draw-list (x top / y d txt i ob)\n  (cp:text (+ x 130.0) (+ top 10.0) 5.0 (cp:ru '(1040 1087 1087 1072 1088 1072 1090 1099 32 1097 1080 1090 1072)) 260.0 \"CP_TEXT\")\n  (setq y (- top 10.0))\n  (foreach d cp:devices\n    (setq txt (strcat (car d) \"   \" (nth 2 d) \"   [\" (cp:s (nth 3 d)) \" DIN]\"))\n    (setq ob (vla-addtext cp:space txt (cp:p x y) 4.0))\n    (vla-put-layer ob \"CP_TEXT\") (vla-put-stylename ob \"CP_GOST\")\n    (setq y (- y 10.0)))\n  (setq ob (vla-addtext cp:space (strcat (cp:ru '(1050 1083 1077 1084 1084 1099 58 32)) (itoa (length cp:terminals)) (cp:ru '(32 1096 1090 46))) (cp:p x (- y 10.0)) 4.0))\n  (vla-put-layer ob \"CP_TEXT\") (vla-put-stylename ob \"CP_GOST\"))"))) nil))
(prin1 (list 490 (if (vl-catch-all-error-p zr) (vl-catch-all-error-message zr) "OK")) zf) (write-line "" zf)
(setq zr (vl-catch-all-apply '(lambda () (eval (read "(defun cp:tag (ob /)\n  (regapp cp:app)\n  (vla-setxdata ob\n    (vlax-safearray-fill (vlax-make-safearray vlax-vbInteger '(0 . 1)) '(1001 1000))\n    (vlax-safearray-fill (vlax-make-safearray vlax-vbVariant '(0 . 1)) (list cp:app (cp:g 'panel))))\n  (vlax-ldata-put ob \"settings\" cp:cfg))"))) nil))
(prin1 (list 502 (if (vl-catch-all-error-p zr) (vl-catch-all-error-message zr) "OK")) zf) (write-line "" zf)
(setq zr (vl-catch-all-apply '(lambda () (eval (read "(defun cp:build (point / blocks name ob oldspace)\n  (cp:layers) (cp:style)\n  (setq blocks (vla-get-blocks cp:doc) name (strcat \"CP_LAYOUT_\" (itoa (abs (getvar \"MILLISECS\")))))\n  (while (tblsearch \"BLOCK\" name) (setq name (strcat name \"_\")))\n  (setq cp:newdef (vla-add blocks (cp:p 0.0 0.0) name) cp:space cp:newdef)\n  (cp:draw-geometry)\n  (setq ob (vla-insertblock (vla-get-modelspace cp:doc) (vlax-3d-point point) name 1.0 1.0 1.0 0.0))\n  (setq cp:pendingnew ob)\n  (vla-put-layer ob \"CP_CASE\") (cp:tag ob) ob)"))) nil))
(prin1 (list 508 (if (vl-catch-all-error-p zr) (vl-catch-all-error-message zr) "OK")) zf) (write-line "" zf)
(setq zr (vl-catch-all-apply '(lambda () (eval (read "(defun cp:pick ( / ss ob cfg)\n  (if (setq ss (entsel (cp:ru '(1042 1099 1073 1077 1088 1080 1090 1077 32 1073 1083 1086 1082 32 1082 1086 1084 1087 1086 1085 1086 1074 1082 1080 58 32))))\n    (progn\n      (setq ob (vlax-ename->vla-object (car ss)))\n      (if (and (= (vla-get-objectname ob) \"AcDbBlockReference\")\n               (assoc -3 (entget (car ss) (list cp:app)))\n               (setq cfg (vlax-ldata-get ob \"settings\")))\n        (list ob cfg)\n        (progn (princ (cp:ru '(1069 1090 1086 32 1085 1077 32 1082 1086 1084 1087 1086 1085 1086 1074 1082 1072 44 32 1089 1086 1079 1076 1072 1085 1085 1072 1103 32 67 80 68 82 65 87 46))) nil)))))"))) nil))
(prin1 (list 517 (if (vl-catch-all-error-p zr) (vl-catch-all-error-message zr) "OK")) zf) (write-line "" zf)
(setq zr (vl-catch-all-apply '(lambda () (eval (read "(defun cp:run (update edit / *error* pick old new point undo path ok cancel)\n  (defun *error* (msg)\n    (cp:close-book) (cp:lib-close)\n    (if (and cp:pendingnew (null new)) (vl-catch-all-apply 'vla-delete (list cp:pendingnew)))\n    (if (and cp:newdef (null new)) (vl-catch-all-apply 'vla-delete (list cp:newdef)))\n    (if undo (vla-endundomark cp:doc))\n    (if (not (member msg '(\"Function cancelled\" \"quit / exit abort\"))) (princ (strcat \"\\nCPDRAW: \" msg)))\n    (princ))\n  (setq cp:doc (vla-get-activedocument (vlax-get-acad-object)) cp:newdef nil cp:measure-cache nil cp:pendingnew nil)\n  (if update\n    (if (setq pick (cp:pick))\n      (setq old (car pick) cp:cfg (cadr pick) point (vlax-safearray->list (vlax-variant-value (vla-get-insertionpoint old))))\n      (setq cancel T))\n    (setq cp:cfg (cp:defaults)))\n  (if (not cancel)\n    (progn\n      (setq path (cp:g 'path))\n      (if (or (null path) (not (findfile path))) (setq path (getfiled (cp:ru '(69 120 99 101 108 32 1089 32 1086 1076 1085 1086 1083 1080 1085 1077 1081 1082 1086 1081)) \"\" \"xlsx;xlsm;xls\" 0)))\n      (if path\n        (progn\n          (cp:put 'path path) (cp:read-book path)\n          (if (null cp:panels) (error (cp:ru '(1042 32 1086 1076 1085 1086 1083 1080 1085 1077 1081 1082 1077 32 1085 1077 1090 32 1097 1080 1090 1086 1074 46))))\n          (if (and update (not (member (cp:g 'panel) cp:panels))) (error (cp:ru '(1057 1086 1093 1088 1072 1085 1105 1085 1085 1099 1081 32 1097 1080 1090 32 1085 1077 32 1085 1072 1081 1076 1077 1085 32 1074 32 69 120 99 101 108 46 32 1048 1089 1087 1086 1083 1100 1079 1091 1081 1090 1077 32 67 80 69 68 73 84 32 1076 1083 1103 32 1074 1099 1073 1086 1088 1072 32 1076 1088 1091 1075 1086 1075 1086 32 1097 1080 1090 1072 46))))\n          (cp:import-library)\n          (setq ok (if edit (cp:dialog) T) cancel (not ok))\n          (if ok (cp:import-library))\n          (while ok\n            (cp:import-library)\n            (cp:collect (cp:g 'panel)) (cp:apply-sizes)\n            (if (or edit (vl-some '(lambda (d) (null (nth 7 d))) cp:devices)) (setq ok (cp:sizes-dialog)))\n            (if ok\n              (if (cp:plan) (setq ok nil)\n                (progn (alert cp:problem) (setq ok (cp:dialog)) (if (not ok) (setq cancel T))))\n              (setq cancel T)))\n          (if (and (not cancel) (null cp:problem))\n            (progn\n              (if (not update) (setq point (getpoint (cp:ru '(1059 1082 1072 1078 1080 1090 1077 32 1083 1077 1074 1099 1081 32 1085 1080 1078 1085 1080 1081 32 1091 1075 1086 1083 32 1082 1086 1088 1087 1091 1089 1072 32 1097 1080 1090 1072 58 32)))))\n              (if point\n                (progn\n                  (if (not update) (setq point (trans point 1 0)))\n                  (vla-startundomark cp:doc) (setq undo T)\n                  (setq new (cp:build point))\n                  (if old\n                    (progn\n                      (vla-put-xscalefactor new (vla-get-xscalefactor old))\n                      (vla-put-yscalefactor new (vla-get-yscalefactor old))\n                      (vla-put-zscalefactor new (vla-get-zscalefactor old))\n                      (vla-put-rotation new (vla-get-rotation old))\n                      (vla-delete old)))\n                  (vlax-ldata-put \"SX_PANEL\" \"last\" cp:cfg)\n                  (vla-endundomark cp:doc) (setq undo nil)\n                  (vla-regen cp:doc 1)\n                  (princ (strcat (cp:ru '(10 1050 1086 1084 1087 1086 1085 1086 1074 1082 1072 32 1087 1086 1089 1090 1088 1086 1077 1085 1072 58 32)) (cp:g 'panel) (cp:ru '(44 32 1072 1087 1087 1072 1088 1072 1090 1086 1074 32)) (itoa (length cp:devices)) (cp:ru '(44 32 1082 1083 1077 1084 1084 32)) (itoa (length cp:terminals)) \".\"))))))\n        (setq cancel T))))\n  (cp:lib-close)\n  (princ)))"))) nil))
(prin1 (list 526 (if (vl-catch-all-error-p zr) (vl-catch-all-error-message zr) "OK")) zf) (write-line "" zf)
(setq zr (vl-catch-all-apply '(lambda () (eval (read "(defun c:CPDRAW () (cp:run nil T))"))) nil))
(prin1 (list 582 (if (vl-catch-all-error-p zr) (vl-catch-all-error-message zr) "OK")) zf) (write-line "" zf)
(setq zr (vl-catch-all-apply '(lambda () (eval (read "(defun c:CPUPDATE () (cp:run T nil))"))) nil))
(prin1 (list 583 (if (vl-catch-all-error-p zr) (vl-catch-all-error-message zr) "OK")) zf) (write-line "" zf)
(setq zr (vl-catch-all-apply '(lambda () (eval (read "(defun c:CPEDIT () (cp:run T T))"))) nil))
(prin1 (list 584 (if (vl-catch-all-error-p zr) (vl-catch-all-error-message zr) "OK")) zf) (write-line "" zf)
(setq zr (vl-catch-all-apply '(lambda () (eval (read "(defun c:CPDELETE ( / pick doc)\n  (if (setq pick (cp:pick))\n    (progn (setq doc (vla-get-activedocument (vlax-get-acad-object)))\n      (vla-startundomark doc) (vla-delete (car pick)) (vla-endundomark doc))) (princ))"))) nil))
(prin1 (list 585 (if (vl-catch-all-error-p zr) (vl-catch-all-error-message zr) "OK")) zf) (write-line "" zf)
(setq zr (vl-catch-all-apply '(lambda () (eval (read "(princ \"\\nSX_Panel v1.0: CPDRAW / CPUPDATE / CPEDIT / CPDELETE\")"))) nil))
(prin1 (list 589 (if (vl-catch-all-error-p zr) (vl-catch-all-error-message zr) "OK")) zf) (write-line "" zf)
(setq zr (vl-catch-all-apply '(lambda () (eval (read "(princ)"))) nil))
(prin1 (list 590 (if (vl-catch-all-error-p zr) (vl-catch-all-error-message zr) "OK")) zf) (write-line "" zf)
(close zf) (princ)
