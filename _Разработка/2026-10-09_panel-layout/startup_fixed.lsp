(vl-load-com)
(load "C:/Users/user/Desktop/02_Справочники_CAD_Revit/odnolineyka/2_AutoCAD/Компоновка/SX_Panel.lsp")
(setenv "CP_DclFile" "C:/Users/user/Desktop/02_Справочники_CAD_Revit/odnolineyka/2_AutoCAD/Компоновка/SX_Panel.dcl")
(setq cppr:f (open "C:/Users/user/Desktop/02_Справочники_CAD_Revit/odnolineyka/_Разработка/2026-10-09_panel-layout/startup_fixed.txt" "w"))
(prin1 (list 'version cp:version 'dcl (cp:dcl-file) 'library (cp:default-library)) cppr:f) (write-line "" cppr:f)
(setq cppr:id (load_dialog (cp:dcl-file)))
(prin1 (list 'main (new_dialog "cp_main" cppr:id)) cppr:f) (write-line "" cppr:f) (done_dialog 0)
(prin1 (list 'sizes (new_dialog "cp_sizes" cppr:id)) cppr:f) (write-line "" cppr:f) (done_dialog 0) (unload_dialog cppr:id)
(setq cppr:r (vl-catch-all-apply 'cp:fail '("Controlled diagnostic test")))
(prin1 (list 'failure (if (vl-catch-all-error-p cppr:r) (vl-catch-all-error-message cppr:r) cppr:r)) cppr:f)
(close cppr:f) (princ)
