(vl-load-com)
(setq ppdoc (vla-get-activedocument (vlax-get-acad-object)) ppms (vla-get-modelspace ppdoc) ppf (open "C:/Users/user/Desktop/02_Справочники_CAD_Revit/odnolineyka/_Разработка/2026-10-09_panel-layout/block_dynamics.txt" "w") ppi 0)
(foreach name '("S201" "S203" "DS201" "DS203" "ABB S201" "Дин" "Шина N" "VPR-2.5-3L-GY" "VPR-6-GY" "VPR-6-BU" "D-VPR-6" "БП DIN" "ESB40" "F204" "3+1")
  (setq x (* (rem ppi 5) 300.0) y (* (fix (/ ppi 5)) -180.0))
  (setq o (vla-insertblock ppms (vlax-3d-point (list x y 0.0)) name 1.0 1.0 1.0 0.0))
  (prin1 (list name (if (= (vla-get-isdynamicblock o) :vlax-true) (mapcar '(lambda (p) (list (vla-get-propertyname p) (vlax-variant-value (vla-get-value p)) (if (vlax-property-available-p p 'AllowedValues) (vlax-variant-value (vla-get-allowedvalues p))))) (vlax-invoke o 'GetDynamicBlockProperties)))) ppf) (write-line "" ppf)
  (vla-addtext ppms name (vlax-3d-point (list x (- y 90.0) 0.0)) 7.0)
  (setq ppi (1+ ppi)))
(close ppf) (vla-regen ppdoc 1) (princ)
