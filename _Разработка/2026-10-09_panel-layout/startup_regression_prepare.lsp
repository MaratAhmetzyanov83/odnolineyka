(vl-load-com)
(if (= (getvar "DWGNAME") "CPDRAW_regression.dwg")
(progn
(load "C:/Users/user/Desktop/02_Справочники_CAD_Revit/odnolineyka/2_AutoCAD/Компоновка/SX_Panel.lsp")
(setq qa:f (open "C:/Users/user/Desktop/02_Справочники_CAD_Revit/odnolineyka/_Разработка/2026-10-09_panel-layout/startup_regression.txt" "w"))
(defun qa:check (key ok) (write-line (strcat key "=" (if ok "PASS" "FAIL")) qa:f))
(defun *error* (msg) (write-line (strcat "ERROR=" msg) qa:f) (close qa:f) (princ))
(setq cp:cfg (cp:defaults)) (cp:put 'path "//Server/DropBox/Работа server/4. Техдепартамент/4.1. Проекты/098 Ташкент-КТ/5 ПИР/5.4_Том 3 ХБК/02_ELD-D1-02-ЭОМ/Таблицы/Однолинейка ЩC-ВК.02.xlsx") (vlax-ldata-put "SX_PANEL" "last" cp:cfg)
(qa:check "folder_absent_from_support_path" (null (findfile "SX_Panel.dcl")))
(qa:check "cached_dialog_resolved" (findfile (cp:dcl-file)))
(qa:check "bundled_library_resolved" (findfile (cp:default-library)))
(setq qa:id (load_dialog (cp:dcl-file)))
(qa:check "main_dialog_loads" (new_dialog "cp_main" qa:id)) (done_dialog 0)
(qa:check "mapping_dialog_loads" (new_dialog "cp_sizes" qa:id)) (done_dialog 0) (unload_dialog qa:id)
;; Автоматизация выбора параметров; саму команду и построение выполняет рабочий LISP.
(defun cp:dialog ()
 (cp:put 'path "//Server/DropBox/Работа server/4. Техдепартамент/4.1. Проекты/098 Ташкент-КТ/5 ПИР/5.4_Том 3 ХБК/02_ELD-D1-02-ЭОМ/Таблицы/Однолинейка ЩC-ВК.02.xlsx")
 (if (not (member (cp:g 'panel) cp:panels)) (cp:put 'panel (car cp:panels)))
 T)
(defun cp:sizes-dialog ( / mapping d)
 (foreach d cp:devices
  (setq mapping (cons (cons (nth 1 d) (list (cp:default-block d) 1.0 0.0 nil)) mapping)))
 (cp:put 'sizes mapping) (cp:apply-sizes) T)
)) (princ)
