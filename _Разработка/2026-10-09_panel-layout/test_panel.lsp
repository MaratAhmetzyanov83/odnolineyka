(vl-load-com)
(if (= (getvar "DWGNAME") "Компоновка_проверка_из_базы.dwg")
(progn
(load "C:/Users/user/Desktop/02_Справочники_CAD_Revit/odnolineyka/2_AutoCAD/Компоновка/SX_Panel.lsp")
(defun *error* (msg) (setq f (open "C:/Users/user/Desktop/02_Справочники_CAD_Revit/odnolineyka/_Разработка/2026-10-09_panel-layout/test_result.txt" "w")) (prin1 (list 'error msg cp:stage) f) (close f) (princ))
(setq cp:doc (vla-get-activedocument (vlax-get-acad-object)) cp:measure-cache nil cp:cfg (cp:defaults))
(cp:put 'path "\\\\Server\\DropBox\\Работа server\\4. Техдепартамент\\4.1. Проекты\\098 Ташкент-КТ\\5 ПИР\\5.4_Том 3 ХБК\\02_ELD-D1-02-ЭОМ\\Таблицы\\Однолинейка ЩC-ВК.01.xlsx") (cp:put 'library "C:\\Users\\user\\Desktop\\02_Справочники_CAD_Revit\\odnolineyka\\База блоков компоновки (1).dwg") (cp:put 'panel "ЩР-1")
(cp:put 'gap 60.0) (cp:put 'nrows 2) (cp:put 'slots 24) (cp:put 'reserve 20.0)
(setq cp:stage "read book") (cp:read-book (cp:g 'path))
(setq cp:stage "library") (cp:import-library)
(setq cp:stage "collect") (cp:collect (cp:g 'panel))
(setq cp:cfg (vl-remove-if '(lambda (p) (= (car p) 'sizes)) cp:cfg) cp:sd nil)
(foreach d cp:devices (setq cp:sd (cons (cons (nth 1 d) (list (cp:default-block d) 1.0 0.0)) cp:sd)))
(setq cp:sd (cons '("@XT" "VPR-2.5-3L-GY" 1.0 0.0) cp:sd))
(cp:put 'sizes cp:sd)
(setq cp:stage "sizes") (cp:apply-sizes)
(setq cp:stage "plan") (setq cp:ok (cp:plan))
(if cp:ok
  (progn
    (setq cp:stage "clear test drawing")
    (vlax-for ob (vla-get-modelspace cp:doc) (vla-delete ob))
    (setq cp:stage "build") (setq cp:result (cp:build '(0.0 0.0 0.0)))
    (vla-regen cp:doc 1) (vla-save cp:doc)))
(setq f (open "C:/Users/user/Desktop/02_Справочники_CAD_Revit/odnolineyka/_Разработка/2026-10-09_panel-layout/test_result.txt" "w"))
(prin1 (list (cons 'ok cp:ok) (cons 'problem cp:problem) (cons 'devices (length cp:devices)) (cons 'rows cp:totalrows) (cons 'sizes cp:sd) (cons 'positions cp:positions) (cons 'block (if cp:result (vla-get-name cp:result)))) f) (close f)
(cp:lib-close))) (princ)
