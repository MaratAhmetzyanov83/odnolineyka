;;; SX_Panel v1.7 — внутренняя компоновка электрощита из Excel.
;;; CPDRAW / CPUPDATE / CPEDIT / CPDELETE / CPEXPLODE. Самостоятельный LISP, SX_Schema не нужен.
;;; Модульные аппараты и клеммы из пользовательской базы; корпус не рисуется.
;;; Excel только читается. Единый блок или отдельные объекты, слои CP_*.
(vl-load-com)
(setq cp:version "1.7" cp:app "SX_PANEL" cp:partsapp "SX_PANEL_PARTS")

;;; Unicode / CP1251: строки работают и при LISPSYS=0.
(defun cp:cp (c)
  (if (= (getvar "LISPSYS") 0)
    (cond ((and (>= c 1040) (<= c 1103)) (- c 848)) ((= c 1025) 168) ((= c 1105) 184) ((= c 8470) 185) (t c)) c))
(defun cp:ru (cs) (apply 'strcat (mapcar '(lambda (c) (chr (cp:cp c))) cs)))
(defun cp:v (v)
  (cond ((= (type v) 'VARIANT) (if (member (vlax-variant-type v) '(0 1 10)) nil (cp:v (vlax-variant-value v))))
        ((and (= (type v) 'STR) (= v "")) nil) (t v)))
(defun cp:s (v)
  (cond ((null v) "") ((= (type v) 'STR) v) ((numberp v) (rtos v 2 2)) (t "")))
(defun cp:fail (message)
  (setq cp:failure T)
  ;; AutoLISP не содержит функцию ERROR. EXIT передаёт управление обработчику.
  (princ (strcat "\nCPDRAW: " message))
  (exit))
(defun cp:dcl-file ( / file source)
  (setq file
    (cond ((and (setq source (findfile "SX_Panel.lsp"))
                (setq file (findfile (strcat (vl-filename-directory source) "/SX_Panel.dcl")))) file)
          ((and (getenv "CP_DclFile") (setq file (findfile (getenv "CP_DclFile")))) file)
          ((findfile "SX_Panel.dcl"))
          ((getfiled "Укажите файл окна SX_Panel.dcl из папки Компоновка" "SX_Panel.dcl" "dcl" 0))))
  (if file (setenv "CP_DclFile" file))
  file)
(defun cp:num (s) (distof (vl-string-translate "," "." s) 2))
(defun cp:norm (s) (strcase (vl-string-trim " " (cp:s s))))
(defun cp:g (key) (cdr (assoc key cp:cfg)))
(defun cp:put (key val)
  (if (assoc key cp:cfg) (setq cp:cfg (subst (cons key val) (assoc key cp:cfg) cp:cfg))
    (setq cp:cfg (cons (cons key val) cp:cfg))))
(defun cp:rel (o) (if (= (type o) 'VLA-OBJECT) (vl-catch-all-apply 'vlax-release-object (list o))))
(defun cp:close-book ()
  (if (and cp:wb cp:opened) (vl-catch-all-apply 'vlax-invoke-method (list cp:wb 'Close :vlax-false)))
  (cp:rel cp:wb)
  (if (and cp:xl cp:created) (vl-catch-all-apply 'vlax-invoke-method (list cp:xl 'Quit)))
  (cp:rel cp:xl)
  (setq cp:wb nil cp:xl nil cp:opened nil cp:created nil))
(defun cp:open-book (path / wbs w)
  (cp:close-book)
  (setq cp:xl (vl-catch-all-apply 'vlax-get-object '("Excel.Application")))
  (if (vl-catch-all-error-p cp:xl) (setq cp:xl (vlax-create-object "Excel.Application") cp:created T))
  (setq wbs (vlax-get-property cp:xl 'Workbooks))
  (vlax-for w wbs
    (if (and (null cp:wb) (= (strcase path) (strcase (vlax-get-property w 'FullName))))
      (setq cp:wb w) (cp:rel w)))
  (if (null cp:wb)
    (setq cp:wb (vlax-invoke-method wbs 'Open path :vlax-false :vlax-true) cp:opened T))
  (cp:rel wbs)
  cp:wb)
(defun cp:range (sheet addr / shs sh rg vals)
  (setq shs (vlax-get-property cp:wb 'Worksheets))
  (setq sh (vl-catch-all-apply 'vlax-get-property (list shs 'Item sheet)))
  (cp:rel shs)
  (if (vl-catch-all-error-p sh) (cp:fail (strcat "Нет листа Excel: " sheet)))
  (setq rg (vlax-get-property sh 'Range addr))
  (setq vals (vl-catch-all-apply '(lambda () (vlax-safearray->list (vlax-variant-value (vlax-get-property rg 'Value2)))) nil))
  (cp:rel rg) (cp:rel sh)
  (if (vl-catch-all-error-p vals) (cp:fail (vl-catch-all-error-message vals)))
  (mapcar '(lambda (r) (mapcar 'cp:v r)) vals))
(defun cp:read-book (path /)
  (cp:open-book path)
  (setq cp:rows (cp:range "Однолинейка" "A3:BY1000")
        cp:catalog (cp:range "Каталог" "A4:P1000") cp:panels nil)
  (foreach r cp:rows (if (and (car r) (not (member (cp:s (car r)) cp:panels))) (setq cp:panels (append cp:panels (list (cp:s (car r)))))))
  (cp:close-book))

;;; Аппарат: (id, ключ, модель, ширина DIN, высота, тип, строка, блок, масштаб, угол).
(defun cp:at (r c) (nth (1- c) r))
(defun cp:words (s / i ch word res)
  (setq i 1 word "")
  (while (<= i (strlen s))
    (setq ch (substr s i 1))
    (if (= ch " ") (progn (if (/= word "") (setq res (cons word res))) (setq word "")) (setq word (strcat word ch)))
    (setq i (1+ i)))
  (if (/= word "") (setq res (cons word res))) (reverse res))
(defun cp:qparts (s / toks poles amp diff tk)
  (setq toks (cp:words (cp:s s)) poles "" amp nil diff nil)
  (foreach tk toks
    (cond ((wcmatch (strcase tk) "#P") (setq poles (strcase tk)))
          ((wcmatch (strcase tk) (strcase "*мА")) (setq diff T))
          ((null amp) (setq amp (cp:num (vl-string-left-trim "ABCDabcd" tk))))))
  ;; distof не принимает букву А на конце; взять ведущую числовую часть.
  (if (null amp)
    (foreach tk toks
      (if (and (null amp) (wcmatch (strcase tk) "[BCD]#*")) (setq amp (atof (substr tk 2))))))
  (list poles amp diff))
(defun cp:qcatalog (r / parts c candidates diff qchar model)
  (setq parts (cp:qparts (cp:at r 8)) candidates nil)
  (foreach c cp:catalog
    (setq diff (= (cp:norm (nth 10 c)) (cp:norm "да")))
    (if (and (member (cp:norm (car c)) (list (cp:norm "Автомат") (cp:norm "Дифавтомат")))
             (= (cp:norm (nth 8 c)) (car parts))
             (numberp (nth 9 c)) (numberp (cadr parts)) (equal (nth 9 c) (cadr parts) 0.001)
             (equal diff (caddr parts)))
      (setq candidates (cons c candidates))))
  ;; При нескольких моделях не угадывать производителя/серию.
  (if (= (length candidates) 1) (car candidates)))
(defun cp:model-catalog (model / matches)
  (foreach c cp:catalog (if (= (cp:norm (nth 2 c)) (cp:norm model)) (setq matches (cons c matches))))
  (if (= (length matches) 1) (car matches)))
(defun cp:add-device (id model cat kind row / key mods)
  (setq key (strcat kind "|" (cp:norm model)) mods (if cat (nth 11 cat)))
  (if (or (not (numberp mods)) (<= mods 0)) (setq mods nil))
  (setq cp:devices (append cp:devices (list (list id key model mods (cp:g 'devh) kind row)))))
(defun cp:cable-section (text / norm at section)
  (setq norm (vl-string-translate "хХX×," "xxxx." (cp:s text)) at (vl-string-search "x" norm))
  (if at (setq section (atof (substr norm (+ at 2)))))
  (if (and section (> section 0)) section))
(defun cp:cable-cores (text / norm at i ch digits count)
  (setq norm (vl-string-translate "хХX×," "xxxx." (cp:s text))
        at (vl-string-search "x" norm) digits "")
  (if at
    (progn
      (setq i at)
      (while (and (> i 0) (= (substr norm i 1) " ")) (setq i (1- i)))
      (while (and (> i 0) (wcmatch (setq ch (substr norm i 1)) "#"))
        (setq digits (strcat ch digits) i (1- i)))
      (setq count (atoi digits))))
  (if (and count (> count 0)) count))
(defun cp:terminal-set (id r / section cores sizes size phases pins color model suffix pin items)
  (setq section (cp:cable-section (cp:at r 17)) cores (cp:cable-cores (cp:at r 17)) sizes '(1.5 2.5 4.0 6.0 10.0 16.0))
  (if (null section) (cp:fail (strcat "Не найдено сечение кабеля для " id ". Проверьте столбец Q.")))
  (setq size (car (vl-remove-if '(lambda (n) (< n section)) sizes)))
  (if (null size) (cp:fail (strcat "Для " id " в базе нет клеммы под сечение " (cp:s section))))
  (setq phases (if (or (= (cp:at r 44) 3) (vl-string-search "," (cp:s (cp:at r 22)))) 3 1))
  (if (and (= cores 3) (<= section 2.5))
    (progn
      (setq model "VPR-2.5-3L-GY"
            items (list (list id (strcat "XT|" model) model nil nil "XT" 0))))
    (progn
      (setq pins (if (= phases 1) '("L" "N" "PE") '("L1" "L2" "L3" "N" "PE")))
      (foreach pin pins
        (setq color (cond ((= pin "N") "BU") ((= pin "PE") (if (= size 1.5) "PE" "PE-YG")) (t "GY"))
              suffix (if (member size '(1.5 2.5)) (rtos size 2 1) (itoa (fix size)))
              model (strcat "VPR-" suffix "-" color))
        (setq items (append items (list (list (strcat id ":" pin) (strcat "XT|" model) model nil nil "XT" 0)))))))
  (setq cp:terminalgroups (append cp:terminalgroups (list (list id items section)))))
(defun cp:apply-terminals ( / groups group items d m bb)
  (setq cp:terminals nil groups nil)
  (foreach group cp:terminalgroups
    (setq items nil)
    (foreach d (cadr group)
      (setq m (cdr (assoc (nth 1 d) (cp:g 'sizes))))
      (if (null m) (setq m (list (nth 2 d) 1.0 0.0)))
      (setq bb (cp:measure (car m) (cadr m) (caddr m) (nth 3 m))
            d (list (car d) (nth 1 d) (nth 2 d) (- (nth 2 bb) (nth 0 bb)) (- (nth 3 bb) (nth 1 bb)) "XT" 0 (car m) (cadr m) (caddr m) (nth 3 m))
            items (append items (list d)) cp:terminals (append cp:terminals (list d))))
    (setq groups (append groups (list (list (car group) items (nth 2 group))))))
  (setq cp:terminalgroups groups))
(defun cp:cross-add ( / counts d r parts ph poles idx need ways banks name prefix k)
  ;; Счёт отходящих подключений по фазам + одно питающее подключение на полюс.
  (setq counts '(0 0 0 0) cp:cross-unknown 0)
  (foreach d cp:devices
    (if (= (nth 5 d) "QF")
      (progn
        (setq r (nth (- (nth 6 d) 3) cp:rows) parts (cp:qparts (cp:at r 8))
              ph (cp:norm (cp:at r 22)) poles (car parts))
        (cond ((member poles '("3P" "4P"))
               (setq counts (list (1+ (car counts)) (1+ (cadr counts)) (1+ (caddr counts)) (nth 3 counts))))
              ((member ph '("L1" "L2" "L3"))
               (setq idx (vl-position ph '("L1" "L2" "L3")))
               (setq counts (mapcar '(lambda (n j) (if (= j idx) (1+ n) n)) counts '(0 1 2 3))))
              (t ;; Без фазы не угадываем: предусматриваем подключение на каждой фазе.
               (setq cp:cross-unknown (1+ cp:cross-unknown)
                     counts (list (1+ (car counts)) (1+ (cadr counts)) (1+ (caddr counts)) (nth 3 counts)))))
        (if (member poles '("2P" "4P")) (setq counts (list (car counts) (cadr counts) (caddr counts) (1+ (nth 3 counts))))))))
  (setq cp:cross-counts counts need (apply 'max counts)
        ways (cond ((<= need 6) 7) ((<= need 10) 11) (t 15))
        banks (max 1 (fix (+ (/ (float need) (1- ways)) 0.999999)))
        name (strcat "EKF_CM_4x" (itoa ways)) cp:cross-banks banks cp:cross-ways ways k 1 prefix nil)
  (repeat banks
    (setq prefix (append prefix (list (list (strcat "XRM" (itoa k)) "CROSS|DISTRIBUTION" name nil (cp:g 'devh) "CROSS" 0))) k (1+ k)))
  (setq cp:devices (append prefix cp:devices)))
(defun cp:collect (panel / selected r idx cat qid mid model n typ txt id seenq seenm seenxt k counts)
  (setq cp:devices nil cp:terminals nil cp:terminalgroups nil selected nil idx 3 counts nil)
  (foreach r cp:rows
    (if (and (= (cp:s (car r)) panel) (numberp (cp:at r 2)) (= (cp:at r 56) 1))
      (setq selected (cons (list r idx) selected)))
    (setq idx (1+ idx)))
  (setq selected (vl-sort selected '(lambda (a b) (< (cp:at (car a) 2) (cp:at (car b) 2)))))
  (foreach rec selected
    (setq r (car rec) idx (cadr rec) qid (cp:s (cp:at r 36)))
    (if (and (/= qid "") (not (member qid seenq)))
      (progn
        (setq seenq (cons qid seenq) cat (cp:qcatalog r)
              model (if cat (cp:s (nth 2 cat)) (cp:s (cp:at r 8))))
        (cp:add-device qid model cat "QF" idx)
        (setq k 0)
        (repeat 3
          (setq typ (cp:s (cp:at r (+ 60 k))) txt (cp:s (cp:at r (+ 9 k))))
          (if (/= typ "")
            (progn
              (setq n (1+ (if (assoc typ counts) (cdr (assoc typ counts)) 0)))
              (if (assoc typ counts) (setq counts (subst (cons typ n) (assoc typ counts) counts)) (setq counts (cons (cons typ n) counts)))
              (setq id (strcat typ (itoa n)) cat (cp:model-catalog txt))
              (cp:add-device id txt cat typ idx)))
          (setq k (1+ k)))))
    (setq mid (cp:s (cp:at r 34)) model (cp:s (cp:at r 35)))
    (if (and (/= mid "") (/= model "") (not (member mid seenm)))
      (progn (setq seenm (cons mid seenm)) (cp:add-device mid model (cp:model-catalog model) "MODULE" idx)))
    (setq txt (cp:s (cp:at r 16)))
    (if (and (= (cp:at r 51) 1) (/= txt "") (not (member txt seenxt)))
      (progn (setq seenxt (cons txt seenxt)) (cp:terminal-set txt r))))
  (foreach group cp:terminalgroups (setq cp:terminals (append cp:terminals (cadr group))))
  (if cp:devices (cp:cross-add))
  cp:devices)
(defun cp:apply-sizes ( / mapping metrics name scale rot)
  (setq cp:devices (mapcar '(lambda (d)
    (setq mapping (cdr (assoc (nth 1 d) (cp:g 'sizes))))
    (if mapping
      (progn
        (setq name (car mapping) scale (cadr mapping) rot (caddr mapping)
              metrics (cp:measure name scale rot (nth 3 mapping)))
        (list (nth 0 d) (nth 1 d) (nth 2 d)
              (/ (- (nth 2 metrics) (nth 0 metrics)) (cp:g 'pitch))
              (- (nth 3 metrics) (nth 1 metrics)) (nth 5 d) (nth 6 d) name scale rot (nth 3 mapping)))
      d)) cp:devices)))

;;; Проверка и раскладка до изменения чертежа.
;;; Позиция: (аппарат, номер рейки, x от начала рейки).
(defun cp:pack (devices capacity pitch / row x placed bad d width)
  (setq row 0 x 0.0)
  (foreach d devices
    (if (not (numberp (nth 3 d))) (setq bad (strcat "Не задана ширина: " (car d)))
      (progn
        (setq width (* (nth 3 d) pitch))
        (if (> width (+ capacity 0.001)) (setq bad (strcat "Аппарат шире доступного места на рейке: " (car d)))
          (progn
            (if (> (+ x width) (+ capacity 0.001)) (setq row (1+ row) x 0.0))
            (setq placed (cons (list d row x) placed) x (+ x width)))))))
  (list (reverse placed) (if devices (1+ row) 0) bad))
(defun cp:endcap (group / model tokens name bb)
  (setq model (nth 2 (car (cadr group))) tokens (cp:words (vl-string-translate "-" " " model))
        name (strcat "D-VPR-" (cadr tokens) (if (wcmatch model "VPR-*-3L-*") "-3L" "")) bb (cp:measure name 1.0 0.0 nil))
  (list "" name name (- (nth 2 bb) (nth 0 bb)) (- (nth 3 bb) (nth 1 bb)) "CAP" 0 name 1.0 0.0 nil))
(defun cp:plan ( / usable packed maxh bb d crossname xtrow xtx groupwidth group remaining cap lastcap closed)
  (setq cp:problem nil cp:positions nil
        cp:railw (* (cp:g 'slots) (cp:g 'pitch))
        usable (* cp:railw (- 1.0 (/ (cp:g 'reserve) 100.0)))
        packed (cp:pack cp:devices usable (cp:g 'pitch)))
  (cond ((null cp:devices) (setq cp:problem "У выбранного щита нет аппаратов для компоновки."))
        ((caddr packed) (setq cp:problem (caddr packed)))
        ((> (cadr packed) (cp:g 'nrows))
         (setq cp:problem (strcat "Нужно рядов: " (itoa (cadr packed)) ". Задано: " (itoa (cp:g 'nrows)) ".")))
        (t (setq cp:positions (car packed))))
  (foreach d cp:devices
    (if (= (nth 5 d) "CROSS")
      (progn
        (setq crossname (nth 7 d))
        (if (or (null crossname) (not (wcmatch crossname "EKF_CM_4x7,EKF_CM_4x11,EKF_CM_4x15")))
          (setq cp:problem "Для кросс-модуля выберите EKF_CM_4x7, EKF_CM_4x11 или EKF_CM_4x15 из вашей базы.")
          (if (< (* cp:cross-banks (1- (atoi (substr crossname 10)))) (apply 'max cp:cross-counts))
            (setq cp:problem "В выбранном кросс-модуле недостаточно подключений. Одно подключение каждого полюса оставлено под питание."))))))
  (cp:apply-terminals)
  (setq cp:xtpositions nil cp:xtrows 0 cp:caps nil xtrow 0 xtx 0.0 remaining cp:terminalgroups closed T)
  (while remaining
    (setq group (car remaining) cap (cp:endcap group)
          groupwidth (apply '+ (mapcar '(lambda (d) (nth 3 d)) (cadr group))))
    (if (> (+ groupwidth (nth 3 cap)) cp:railw) (setq cp:problem (strcat "Набор клемм " (car group) " с заглушкой шире ряда.")))
    (if (> (+ xtx groupwidth (nth 3 cap)) cp:railw)
      (progn
        (if (not closed)
          (setq cp:xtpositions (append cp:xtpositions (list (list lastcap xtrow xtx))) cp:caps (cons lastcap cp:caps)))
        (setq xtrow (1+ xtrow) xtx 0.0)))
    (foreach d (cadr group)
      (setq cp:xtpositions (append cp:xtpositions (list (list d xtrow xtx))) xtx (+ xtx (nth 3 d))))
    (setq closed (or (null (cdr remaining))
                     (/= (nth 7 cap) (nth 7 (cp:endcap (cadr remaining))))))
    (if closed
      (setq cp:xtpositions (append cp:xtpositions (list (list cap xtrow xtx))) cp:caps (cons cap cp:caps) xtx (+ xtx (nth 3 cap))))
    (setq lastcap cap remaining (cdr remaining)))
  (if cp:terminals (setq cp:xtrows (1+ xtrow)))
  (setq cp:totalrows (+ (cp:g 'nrows) cp:xtrows)
        maxh (apply 'max (append (list (cp:g 'devh)) (mapcar '(lambda (d) (nth 4 d)) cp:terminals) (mapcar '(lambda (d) (nth 4 d)) cp:caps) (mapcar '(lambda (d) (nth 4 d)) cp:devices)))
        cp:rowpitch (if (cp:g 'railpitch) (cp:g 'railpitch) (+ maxh (cp:g 'gap)))
        cp:rowtop (+ (/ maxh 2.0) (* (1- cp:totalrows) cp:rowpitch)))
  (cp:put 'w cp:railw)
  (cp:put 'h (+ maxh (* (1- cp:totalrows) cp:rowpitch)))
  (null cp:problem))

(defun cp:railpitch-default (cfg / value height gap)
  (setq value (cdr (assoc 'railpitch cfg)) height (cdr (assoc 'devh cfg)) gap (cdr (assoc 'gap cfg)))
  (if (and (numberp value) (> value 0)) value
    (+ (if (numberp height) height 90.0) (if (numberp gap) gap 60.0))))
(defun cp:label-height (key fallback / value)
  (setq value (cp:g key))
  (if (and (numberp value) (> value 0)) value fallback))
(defun cp:defaults ( / cfg last)
  (setq cfg '((nrows . 3) (slots . 24) (pitch . 18.0) (reserve . 20.0)
              (gap . 60.0) (devh . 90.0)))
  (if (setq last (vlax-ldata-get "SX_PANEL" "last")) (setq cfg last))
  (if (null (assoc 'railpitch cfg)) (setq cfg (cons (cons 'railpitch (cp:railpitch-default cfg)) cfg)))
  (if (null (assoc 'textheight cfg)) (setq cfg (cons '(textheight . 4.0) cfg)))
  (if (null (assoc 'xttextheight cfg)) (setq cfg (cons '(xttextheight . 2.0) cfg)))
  (if (null (assoc 'oneblock cfg)) (setq cfg (cons '(oneblock . T) cfg)))
  (if (null (assoc 'gap cfg)) (setq cfg (cons '(gap . 60.0) cfg)))
  (if (null (assoc 'library cfg)) (setq cfg (cons (cons 'library (cp:default-library)) cfg)))
  (if (null (assoc 'path cfg)) (setq cfg (cons (cons 'path (getenv "SX_LastXls")) cfg)))
  (if (null (assoc 'panel cfg)) (setq cfg (cons (cons 'panel (getenv "SX_LastPanel")) cfg)))
  cfg)

(defun cp:cfg-save ( / key val good)
  (setq good T)
  (foreach key '(nrows slots pitch reserve railpitch devh textheight xttextheight)
    (setq val (cp:num (get_tile (strcase (vl-symbol-name key) T))))
    (if (or (null val) (if (= key 'reserve) (or (< val 0) (>= val 100)) (<= val 0))
            (and (member key '(nrows slots)) (not (equal val (fix val) 0.000001))))
      (setq good nil)
      (cp:put key (if (member key '(nrows slots)) (fix val) val))))
  (if good
    (progn (cp:put 'oneblock (= (get_tile "oneblock") "1")) (cp:put 'library (get_tile "library")) (cp:put 'panel (nth (atoi (get_tile "panel")) cp:panels)) (done_dialog 1))
    (set_tile "status" "Проверьте размеры и целое количество реек/модулей. Резерв: 0–99 %.")))
(defun cp:dialog ( / id res key path)
  (cp:put 'railpitch (cp:railpitch-default cp:cfg))
  (cp:put 'textheight (cp:label-height 'textheight 4.0))
  (cp:put 'xttextheight (cp:label-height 'xttextheight 2.0))
  (if (null (setq path (cp:dcl-file))) (exit))
  (if (or (null (cp:g 'library)) (= (cp:g 'library) "") (not (findfile (cp:g 'library))))
    (cp:put 'library (cp:default-library)))
  (setq id (load_dialog path) res 2)
  (if (< id 0) (cp:fail (strcat "Не удалось загрузить файл окна: " path)))
  (while (= res 2)
    (if (not (new_dialog "cp_main" id)) (cp:fail "Не удалось открыть окно компоновки."))
    (set_tile "file" (cp:s (cp:g 'path)))
    (set_tile "library" (cp:s (cp:g 'library)))
    (start_list "panel") (mapcar 'add_list cp:panels) (end_list)
    (set_tile "panel" (itoa (if (member (cp:g 'panel) cp:panels) (vl-position (cp:g 'panel) cp:panels) 0)))
    (foreach key '(nrows slots pitch reserve railpitch devh textheight xttextheight)
      (set_tile (strcase (vl-symbol-name key) T) (cp:s (cp:g key))))
    (set_tile "oneblock" (if (if (assoc 'oneblock cp:cfg) (cp:g 'oneblock) T) "1" "0"))
    (action_tile "browse" "(done_dialog 2)")
    (action_tile "accept" "(cp:cfg-save)") (action_tile "cancel" "(done_dialog 0)")
    (setq res (start_dialog))
    (if (= res 2)
      (if (setq path (getfiled "Excel с однолинейкой" (cp:g 'path) "xlsx;xlsm;xls" 0))
        (progn (cp:put 'path path) (cp:read-book path)))))
  (unload_dialog id)
  (= res 1))
(defun cp:size-fill ( / item size name)
  (setq item (nth cp:size-i cp:size-items) size (cdr (assoc (car item) cp:size-data)) name (car size))
  (set_tile "model" (cadr item))
  (set_tile "block" (itoa (if (member name cp:blocknames) (vl-position name cp:blocknames) 0)))
  (set_tile "scale" (cp:s (if (cadr size) (cadr size) 1.0)))
  (set_tile "rotation" (cp:s (if (caddr size) (caddr size) 0.0)))
  (cp:state-list (if name name "") (nth 3 size)))
(defun cp:size-store ( / key name scale rot size state)
  (setq key (car (nth cp:size-i cp:size-items)) name (nth (atoi (get_tile "block")) cp:blocknames)
        scale (cp:num (get_tile "scale")) rot (cp:num (get_tile "rotation")))
  (if (and name (/= name "") scale (> scale 0) rot)
    (progn
      (setq state (nth (atoi (get_tile "state")) cp:state-options) size (cons key (list name scale rot state)))
      (setq cp:size-data (if (assoc key cp:size-data) (subst size (assoc key cp:size-data) cp:size-data) (cons size cp:size-data))) T)
    (progn (set_tile "status" "Выберите ваш блок, положительный масштаб и угол поворота.") nil)))
(defun cp:size-select (new)
  (if (cp:size-store) (progn (setq cp:size-i (atoi new)) (cp:size-fill))
    (set_tile "items" (itoa cp:size-i))))
(defun cp:size-accept ()
  (if (cp:size-store)
    (if (vl-some '(lambda (p) (or (null (cadr p)) (= (cadr p) ""))) cp:size-data)
      (set_tile "status" "Назначьте ваш блок каждой позиции. Пустые позиции отмечены знаком ?." )
      (done_dialog 1))))
(defun cp:sizes-dialog ( / id res key d size name label path)
  (setq cp:size-items nil cp:size-data nil cp:size-i 0)
  (foreach d cp:devices
    (setq key (nth 1 d) size (cdr (assoc key (cp:g 'sizes))))
    (if (null size) (setq size (list (cp:default-block d) 1.0 0.0)))
    (if (not (assoc key cp:size-items))
      (progn
        (setq label (strcat (if (car size) "" "? ") (car d) " — " (nth 2 d)))
        (setq cp:size-items (append cp:size-items (list (list key label))))
        (setq cp:size-data (cons (cons key size) cp:size-data)))))
  (foreach d cp:terminals
    (setq key (nth 1 d) size (cdr (assoc key (cp:g 'sizes))))
    (if (null size) (setq size (list (nth 2 d) 1.0 0.0)))
    (if (not (assoc key cp:size-items))
      (setq cp:size-items (append cp:size-items (list (list key (strcat "Клеммы: " (nth 2 d)))))
            cp:size-data (cons (cons key size) cp:size-data))))
  (if (null (setq path (cp:dcl-file))) (exit))
  (setq id (load_dialog path))
  (if (< id 0) (cp:fail (strcat "Не удалось загрузить файл окна: " path)))
  (if (not (new_dialog "cp_sizes" id)) (cp:fail "Не удалось открыть окно выбора блоков."))
  (start_list "items") (mapcar '(lambda (p) (add_list (cadr p))) cp:size-items) (end_list)
  (start_list "block") (mapcar 'add_list cp:blocknames) (end_list)
  (set_tile "items" "0") (cp:size-fill)
  (action_tile "items" "(cp:size-select $value)")
  (action_tile "block" "(cp:block-choice $value)")
  (action_tile "apply" "(cp:size-store)")
  (action_tile "accept" "(cp:size-accept)") (action_tile "cancel" "(done_dialog 0)")
  (setq res (start_dialog)) (unload_dialog id)
  (if (= res 1) (progn (cp:put 'sizes cp:size-data) (cp:apply-sizes) T)))


;;; Импортируются именно пользовательские определения блоков, без их перерисовки.
(defun cp:default-library ( / base file)
  (setq base (cond ((findfile "SX_Panel.lsp"))
                   ((and (getenv "CP_DclFile")
                         (setq file (findfile (getenv "CP_DclFile")))) file)))
  ;; AND в AutoLISP возвращает T. Путь возвращаем отдельным выражением.
  ;; База рядом (2_AutoCAD/Блоки), иначе Google Диск.
  (cond ((and base (setq file (findfile (strcat (vl-filename-directory base) "/../Блоки/SX_Компоновка_пользовательские.dwg")))) file)
        ((findfile "G:/Мой диск/Однолинейка_базы/SX_Компоновка_пользовательские.dwg"))))

(defun cp:lib-close ()
  (if cp:libdbx (cp:rel cp:libdbx))
  (setq cp:libdbx nil cp:libsrc nil cp:libpath nil))
(defun cp:import-library ( / path b dest)
  ;; Здесь читаем имена, определения копируются только по запросу cp:ensure-block.
  (setq path (cp:g 'library) dest (vla-get-blocks cp:doc))
  (if (and path (/= path "") (findfile path))
    (progn
      (if (not (equal cp:libpath path))
        (progn
          (cp:lib-close)
          (vlax-for d (vla-get-documents (vlax-get-acad-object))
            (if (= (strcase (vla-get-fullname d)) (strcase path)) (setq cp:libsrc d)))
          (if (null cp:libsrc)
            (progn
              (setq cp:libdbx (vla-getinterfaceobject (vlax-get-acad-object) (strcat "ObjectDBX.AxDbDocument." (substr (getvar "ACADVER") 1 2))))
              (vla-open cp:libdbx path) (setq cp:libsrc cp:libdbx)))
          (setq cp:libpath path)))))
  (setq cp:blocknames (list "") cp:casenames nil)
  (if cp:libsrc
    (vlax-for b (vla-get-blocks cp:libsrc)
      (if (and (= (vla-get-isxref b) :vlax-false) (= (vla-get-islayout b) :vlax-false)
               (not (wcmatch (vla-get-name b) "`**,CP_*,*_G###,DKC_*,R5*,DIN_*,SX_DYN_CQEN*,SX_DYN_PLASTRON*,SX_DYN_DIN*")))
        (setq cp:blocknames (cons (vla-get-name b) cp:blocknames)))))
  (vlax-for b dest
    (if (and (not (wcmatch (vla-get-name b) "`**,CP_*,*_G###,DKC_*,R5*,DIN_*,SX_DYN_CQEN*,SX_DYN_PLASTRON*,SX_DYN_DIN*"))
             (= (vla-get-isxref b) :vlax-false) (= (vla-get-islayout b) :vlax-false)
             (not (member (vla-get-name b) cp:blocknames)))
      (setq cp:blocknames (cons (vla-get-name b) cp:blocknames))))
  (setq cp:blocknames (vl-sort cp:blocknames '<))
  cp:blocknames)

(defun cp:ensure-block (name / b arr result)
  (if (not (tblsearch "BLOCK" name))
    (progn
      (if (null cp:libsrc) (cp:fail (strcat "Нет блока в чертеже и не открыта библиотека: " name)))
      (setq b (vl-catch-all-apply 'vla-item (list (vla-get-blocks cp:libsrc) name)))
      (if (vl-catch-all-error-p b) (cp:fail (strcat "В библиотеке нет блока: " name)))
      (setq arr (vlax-make-safearray vlax-vbObject '(0 . 0))) (vlax-safearray-fill arr (list b))
      (setq result (vl-catch-all-apply 'vla-copyobjects (list cp:libsrc arr (vla-get-blocks cp:doc))))
      (if (vl-catch-all-error-p result) (cp:fail (vl-catch-all-error-message result))))))
(defun cp:set-state (ob state / prop allowed found)
  (if (and state (/= state "") (= (vla-get-isdynamicblock ob) :vlax-true))
    (progn
      (foreach prop (vlax-invoke ob 'GetDynamicBlockProperties)
        (setq allowed (cp:dyn-values prop))
        (if (member state allowed)
          (progn (vla-put-value prop (vlax-make-variant state (vlax-variant-type (vla-get-value prop)))) (setq found T))))
      (if (null found) (cp:fail (strcat "Нет исполнения динамического блока: " state)))))
  (vla-update ob))
(defun cp:dyn-values (prop / vals)
  (setq vals (vl-catch-all-apply
    '(lambda ()
       (setq vals (cp:v (vla-get-allowedvalues prop)))
       (if (= (type vals) 'SAFEARRAY)
         (vl-remove-if-not '(lambda (v) (= (type v) 'STR)) (mapcar 'cp:v (vlax-safearray->list vals))))) nil))
  (if (not (vl-catch-all-error-p vals)) vals))
(defun cp:states (name / tmp ob result prop)
  (cp:ensure-block name)
  (setq tmp (vla-add (vla-get-blocks cp:doc) (cp:p 0.0 0.0) (strcat "CP_STATES_" (itoa (abs (getvar "MILLISECS"))))))
  (setq ob (vla-insertblock tmp (cp:p 0.0 0.0) name 1.0 1.0 1.0 0.0))
  (if (= (vla-get-isdynamicblock ob) :vlax-true)
    (foreach prop (vlax-invoke ob 'GetDynamicBlockProperties) (setq result (append result (cp:dyn-values prop)))))
  (vla-delete ob) (vla-delete tmp)
  (cons "" result))
(defun cp:state-list (name state)
  (setq cp:state-options (if (/= name "") (cp:states name) (list "")))
  (start_list "state") (mapcar 'add_list cp:state-options) (end_list)
  (set_tile "state" (itoa (if (member state cp:state-options) (vl-position state cp:state-options) 0))))
(defun cp:block-choice (index)
  (cp:state-list (nth (atoi index) cp:blocknames) ""))


(defun cp:default-block (d / parts name row)
  (setq name (nth 2 d))
  (if (and (= (nth 5 d) "QF") (numberp (nth 6 d)) (>= (nth 6 d) 3)
           (< (- (nth 6 d) 3) (length cp:rows)))
    (setq row (nth (- (nth 6 d) 3) cp:rows)))
  (setq parts (cp:qparts (if (and row (cp:at row 8)) (cp:at row 8) name)))
  (cond
    ((and (= (nth 5 d) "QF") (caddr parts) (= (car parts) "2P")) "DA_1PN_36")
    ((member name cp:blocknames) name)
    ((member (strcat name "_FRONT") cp:blocknames) (strcat name "_FRONT"))
    ((= (nth 5 d) "QF")
     (cond ((and (caddr parts) (member (car parts) '("3P" "4P"))) "DA_4P_135")
           ((= (car parts) "1P") "AV_1P_18") ((= (car parts) "2P") "AV_2P_36")
           ((= (car parts) "3P") "AV_3P_54") ((= (car parts) "4P") "AV_4P_72")))
    ((= (nth 5 d) "KM") "CT_ACDC_4P_63A_FRONT")
    ((= (nth 5 d) "PS") (if (member "ARV-DRP480-PFC-24" cp:blocknames) "ARV-DRP480-PFC-24" nil))))
(defun cp:measure (name scale rot state / key cached blocks tmp ob p1 p2 result)
  (setq key (list name scale rot state))
  (if (setq cached (assoc key cp:measure-cache)) (cdr cached)
    (progn
      (cp:ensure-block name)
      (setq blocks (vla-get-blocks cp:doc) tmp (vla-add blocks (cp:p 0.0 0.0) (strcat "CP_MEASURE_" (itoa (abs (getvar "MILLISECS"))))))
      (setq ob (vla-insertblock tmp (cp:p 0.0 0.0) name scale scale scale (* pi (/ rot 180.0))))
      (cp:set-state ob state)
      (vla-getboundingbox ob 'p1 'p2)
      (setq p1 (vlax-safearray->list p1) p2 (vlax-safearray->list p2) result (list (car p1) (cadr p1) (car p2) (cadr p2)))
      (vla-delete ob) (vla-delete tmp)
      (if (or (< (- (nth 2 result) (nth 0 result)) 0.01) (< (- (nth 3 result) (nth 1 result)) 0.01)) (cp:fail (strcat "Неверные габариты блока: " name)))
      (setq cp:measure-cache (cons (cons key result) cp:measure-cache)) result)))
(defun cp:mapping (key) (cdr (assoc key (cp:g 'sizes))))




(defun cp:place-block (mapping x y lay id / name scale rot bb ob att)
  (setq name (car mapping) scale (cadr mapping) rot (caddr mapping) bb (cp:measure name scale rot (nth 3 mapping)))
  (setq ob (vla-insertblock cp:space (cp:p (- x (nth 0 bb)) (- y (/ (+ (nth 1 bb) (nth 3 bb)) 2.0))) name scale scale scale (* pi (/ rot 180.0))))
  (cp:set-state ob (nth 3 mapping))
  (vla-put-layer ob lay)
  (if (and id (= (vla-get-hasattributes ob) :vlax-true))
    (foreach att (vlax-invoke ob 'GetAttributes)
      (if (member (strcase (vla-get-tagstring att)) (list "ID" "QF" "XT" "TAG" "NAME" "1" (strcase "КМ"))) (vla-put-textstring att id))))
  ob)

;;; Геометрия блока. Все точки локальные, миллиметры, масштаб 1:1.
(defun cp:p (x y) (vlax-3d-point (list x y 0.0)))
(defun cp:layer (name color / lay)
  (setq lay (vl-catch-all-apply 'vla-item (list (vla-get-layers cp:doc) name)))
  (if (vl-catch-all-error-p lay) (setq lay (vla-add (vla-get-layers cp:doc) name)))
  (vla-put-color lay color) name)
(defun cp:layers ()
  (foreach p '(("CP_DEVICES" 7) ("CP_TEXT" 7)) (cp:layer (car p) (cadr p))))

(defun cp:style ( / st)
  (setq st (vl-catch-all-apply 'vla-item (list (vla-get-textstyles cp:doc) "CP_GOST")))
  (if (vl-catch-all-error-p st) (setq st (vla-add (vla-get-textstyles cp:doc) "CP_GOST")))
  (vla-setfont st "GOST 2.304 type A" :vlax-false :vlax-false 204 34)
  (vla-put-height st 0.0) (vla-put-width st 1.0))
(defun cp:line (x1 y1 x2 y2 lay / ob)
  (setq ob (vla-addline cp:space (cp:p x1 y1) (cp:p x2 y2))) (vla-put-layer ob lay) ob)
(defun cp:rect (x1 y1 x2 y2 lay / ob pts)
  (setq pts (vlax-make-safearray vlax-vbDouble '(0 . 7)))
  (vlax-safearray-fill pts (list x1 y1 x2 y1 x2 y2 x1 y2))
  (setq ob (vla-addlightweightpolyline cp:space pts))
  (vla-put-closed ob :vlax-true) (vla-put-layer ob lay) ob)
(defun cp:text (x y h text width lay / ob bb1 bb2 actual)
  (setq ob (vla-addtext cp:space text (cp:p x y) h))
  (vla-put-stylename ob "CP_GOST") (vla-put-layer ob lay)
  (vla-put-alignment ob 10) (vla-put-textalignmentpoint ob (cp:p x y))
  (vla-getboundingbox ob 'bb1 'bb2)
  (setq actual (- (car (vlax-safearray->list bb2)) (car (vlax-safearray->list bb1))))
  (if (and (> width 0) (> actual width)) (vla-put-scalefactor ob (/ width actual)))
  ob)
(defun cp:circle (x y r lay / ob)
  (setq ob (vla-addcircle cp:space (cp:p x y) r)) (vla-put-layer ob lay))
(defun cp:dim (x1 y1 x2 y2 xt yt / ob)
  (setq ob (vla-adddimaligned cp:space (cp:p x1 y1) (cp:p x2 y2) (cp:p xt yt)))
  (vla-put-layer ob "CP_DIMS") (vla-put-textheight ob 4.0) (vla-put-arrowheadsize ob 3.0)
  (vla-put-textstyle ob "CP_GOST") (vla-put-linearscalefactor ob 1.0)
  (vla-put-primaryunitsprecision ob 0) (vla-put-textoverride ob "<>"))
(defun cp:yc (row) (- cp:rowtop (* row cp:rowpitch)))
(defun cp:device (pos left / d x y w h ob part tk curve at tag rating)
  (setq d (car pos) x (+ left (nth 2 pos)) y (cp:yc (cadr pos)) w (* (nth 3 d) (cp:g 'pitch)) h (nth 4 d))
  (setq ob (cp:place-block (list (nth 7 d) (nth 8 d) (nth 9 d) (nth 10 d)) x y "CP_DEVICES" (car d)))
  (if (and (= (nth 5 d) "QF") (= (vla-get-hasattributes ob) :vlax-true))
    (progn
      (setq rating (cp:s (cp:at (nth (- (nth 6 d) 3) cp:rows) 8)) part (cp:qparts rating))
      (foreach tk (cp:words rating) (if (wcmatch (strcase tk) "[BCD]#*") (setq curve (substr (strcase tk) 1 1))))
      (foreach at (vlax-invoke ob 'GetAttributes)
        (setq tag (strcase (vla-get-tagstring at)))
        (cond ((= tag "IN_A") (vla-put-textstring at (if (cadr part) (rtos (cadr part) 2 0) "")))
              ((= tag "CURVE") (vla-put-textstring at (if curve curve "")))
              ((= tag "POLES") (vla-put-textstring at (car part)))
              ((= tag "DESCRIPTION") (vla-put-textstring at (nth 2 d)))))))
  (cp:text (+ x (/ w 2.0)) (+ y (/ h 2.0) 8.0) (cp:label-height 'textheight 4.0) (car d) (- w 2.0) "CP_TEXT"))
(defun cp:draw-geometry ( / w h pos xti tr y x ob)
  (setq w (cp:g 'w) h (cp:g 'h))
  (cp:text (/ w 2.0) (+ h 22.0) 6.0 (strcat "Компоновка аппаратов " (cp:g 'panel)) w "CP_TEXT")
  (foreach pos cp:positions (cp:device pos 0.0))
  (foreach pos cp:xtpositions
    (setq d (car pos) y (cp:yc (+ (cp:g 'nrows) (cadr pos))) x (nth 2 pos))
    (cp:place-block (list (nth 7 d) (nth 8 d) (nth 9 d) (nth 10 d)) x y "CP_DEVICES" (car d))
    (if (/= (nth 5 d) "CAP")
      (progn
        (setq ob (cp:text (+ x (/ (nth 3 d) 2.0)) (+ y (/ (nth 4 d) 2.0) 17.0) (cp:label-height 'xttextheight 2.0) (car d) 33.0 "CP_TEXT"))
        (vla-put-rotation ob (/ pi 2.0)))))
  (cp:draw-list (+ w 35.0) h)
  (cp:text (/ w 2.0) -22.0 4.0
    (strcat "Кросс-модуль: L1=" (itoa (car cp:cross-counts)) "; L2=" (itoa (cadr cp:cross-counts))
            "; L3=" (itoa (caddr cp:cross-counts)) "; N=" (itoa (nth 3 cp:cross-counts)) "; + питание на полюс")
    (+ w 20.0) "CP_TEXT")
  (if (> cp:cross-unknown 0)
    (cp:text (/ w 2.0) -34.0 3.5 "Фазы части автоматов не заданы: место предусмотрено на каждой фазе." w "CP_TEXT")))

(defun cp:draw-list (x top / y d txt i ob)
  (cp:text (+ x 130.0) (+ top 10.0) 5.0 "Аппараты щита" 260.0 "CP_TEXT")
  (setq y (- top 10.0))
  (foreach d cp:devices
    (setq txt (strcat (car d) "   " (nth 2 d) "   [" (cp:s (nth 3 d)) " DIN]"))
    (setq ob (vla-addtext cp:space txt (cp:p x y) 4.0))
    (vla-put-layer ob "CP_TEXT") (vla-put-stylename ob "CP_GOST")
    (setq y (- y 10.0)))
  )

;;; Родительский блок и сохранённые параметры. Обновление меняет только выбранную компоновку.
(defun cp:tag (ob /)
  (regapp cp:app)
  (vla-setxdata ob
    (vlax-safearray-fill (vlax-make-safearray vlax-vbInteger '(0 . 1)) '(1001 1000))
    (vlax-safearray-fill (vlax-make-safearray vlax-vbVariant '(0 . 1)) (list cp:app (cp:g 'panel))))
  (vlax-ldata-put ob "settings" cp:cfg))
(defun cp:build (point / blocks name ob oldspace)
  (cp:layers) (cp:style)
  (setq blocks (vla-get-blocks cp:doc) name (strcat "CP_LAYOUT_" (itoa (abs (getvar "MILLISECS")))))
  (while (tblsearch "BLOCK" name) (setq name (strcat name "_")))
  (setq cp:newdef (vla-add blocks (cp:p 0.0 0.0) name) cp:space cp:newdef)
  (cp:draw-geometry)
  (setq ob (vla-insertblock (vla-get-modelspace cp:doc) (vlax-3d-point point) name 1.0 1.0 1.0 0.0))
  (setq cp:pendingnew ob)
  (vla-put-layer ob "CP_DEVICES") (cp:tag ob) ob)
(defun cp:block-frame (ob)
  (list (vlax-safearray->list (vlax-variant-value (vla-get-insertionpoint ob)))
        (vla-get-xscalefactor ob) (vla-get-yscalefactor ob) (vla-get-zscalefactor ob) (vla-get-rotation ob)))
(defun cp:part-id (entity / data)
  (if (setq data (cadr (assoc -3 (entget entity (list cp:partsapp))))) (cdr (assoc 1000 (cdr data)))))
(defun cp:part-tag (entity id)
  (regapp cp:partsapp)
  (entmod (append (entget entity) (list (list -3 (list cp:partsapp (cons 1000 id)))))))
(defun cp:part-pose (entity / data kind point factor)
  (setq data (entget entity) kind (cdr (assoc 0 data)))
  (if (member kind '("TEXT" "MTEXT" "INSERT"))
    (progn
      (setq point (if (and (= kind "TEXT") (or (/= (cdr (assoc 72 data)) 0) (/= (cdr (assoc 73 data)) 0)))
                    (cdr (assoc 11 data)) (cdr (assoc 10 data)))
            factor (cdr (assoc (if (= kind "INSERT") 41 40) data)))
      (if (and point factor (> factor 0)) (list point (if (assoc 50 data) (cdr (assoc 50 data)) 0.0) factor)))))
(defun cp:parts-entities (id record / result handle entity)
  (foreach handle (cdr (assoc 'handles record))
    (if (and (setq entity (handent handle)) (entget entity) (equal (cp:part-id entity) id)) (setq result (cons entity result))))
  (reverse result))
(defun cp:parts-frame (id record / frame anchor entity current previous delta factor vector rotated)
  (setq frame (cdr (assoc 'frame record)))
  ;; Title is normally the first anchor. Deleted members are skipped; moving the whole layout retains its frame.
  (foreach anchor (cdr (assoc 'anchors record))
    (if (and (null current) (setq entity (handent (car anchor))) (entget entity) (equal (cp:part-id entity) id)
             (setq current (cp:part-pose entity))) (setq previous (cdr anchor))))
  (if (and current previous)
    (progn
      (setq delta (- (cadr current) (cadr previous)) factor (/ (caddr current) (caddr previous))
            vector (mapcar '- (car previous) (car frame))
            rotated (list (- (* (car vector) (cos delta)) (* (cadr vector) (sin delta)))
                          (+ (* (car vector) (sin delta)) (* (cadr vector) (cos delta))) (caddr vector)))
      (list (mapcar '- (car current) (mapcar '(lambda (n) (* n factor)) rotated))
            (* (nth 1 frame) factor) (* (nth 2 frame) factor) (* (nth 3 frame) factor) (+ (nth 4 frame) delta)))
    frame))
(defun cp:parts-pick (entity / id record entities)
  (if (and (setq id (cp:part-id entity)) (setq record (vlax-ldata-get cp:partsapp id))
           (member (cdr (assoc 5 (entget entity))) (cdr (assoc 'handles record))))
    (progn
      (setq entities (cp:parts-entities id record))
      (list (list 'parts id entities) (cdr (assoc 'settings record)) (cp:parts-frame id record)))))
(defun cp:container-delete (container / entity deleted result failed)
  (if (and (= (type container) 'LIST) (= (car container) 'parts))
    (progn
      (foreach entity (caddr container)
        (if (and (not failed) (entget entity))
          (progn
            (setq result (vl-catch-all-apply 'entdel (list entity)))
            (if (or (vl-catch-all-error-p result) (null result)) (setq failed T) (setq deleted (cons entity deleted))))))
      (if failed
        (progn
          (foreach entity deleted (entdel entity))
          (cp:fail "Не удалось удалить компоновку. Проверьте блокировку её слоёв."))
        (vlax-ldata-delete cp:partsapp (cadr container))))
    (vla-delete container)))
(defun cp:cleanup-new ( / entity)
  (foreach entity cp:pendingparts (if (entget entity) (entdel entity)))
  (if cp:pendinggroup (vlax-ldata-delete cp:partsapp cp:pendinggroup))
  (if cp:pendingnew (vl-catch-all-apply 'vla-delete (list cp:pendingnew)))
  (if cp:newdef (vl-catch-all-apply 'vla-delete (list cp:newdef)))
  (setq cp:pendingparts nil cp:pendinggroup nil cp:pendingnew nil cp:newdef nil))
(defun cp:separate (ob frame / id result entity owner before cursor handles anchors pose record)
  ;; Only the outer layout is exploded. Collect new entities directly, including non-uniformly scaled output.
  (setq entity (vlax-vla-object->ename ob) owner (cdr (assoc 330 (entget entity))) before (entlast)
        result (vl-catch-all-apply 'vla-explode (list ob)) cursor (entnext before) cp:pendingparts nil)
  (while cursor
    (if (equal owner (cdr (assoc 330 (entget cursor)))) (setq cp:pendingparts (cons cursor cp:pendingparts)))
    (setq cursor (entnext cursor)))
  (setq cp:pendingparts (reverse cp:pendingparts))
  (if (or (vl-catch-all-error-p result) (null cp:pendingparts)) (cp:fail "Не удалось разделить компоновку. Исходный блок сохранён."))
  (setq id (strcat "CP_PARTS_" (itoa (abs (getvar "MILLISECS")))))
  (while (vlax-ldata-get cp:partsapp id) (setq id (strcat id "_")))
  (foreach entity cp:pendingparts
    (if (null (cp:part-tag entity id)) (cp:fail "Не удалось разделить компоновку. Исходный блок сохранён."))
    (setq handles (cons (cdr (assoc 5 (entget entity))) handles))
    (if (setq pose (cp:part-pose entity)) (setq anchors (cons (cons (cdr (assoc 5 (entget entity))) pose) anchors))))
  (setq record (list (cons 'settings cp:cfg) (cons 'frame frame) (cons 'handles (reverse handles)) (cons 'anchors (reverse anchors)))
        cp:pendinggroup id)
  (vlax-ldata-put cp:partsapp id record)
  (vla-delete ob) (setq cp:pendingnew nil)
  (if cp:newdef (progn (vl-catch-all-apply 'vla-delete (list cp:newdef)) (setq cp:newdef nil)))
  (list 'parts id cp:pendingparts))
(defun cp:pick ( / ss ob cfg parts)
  (if (setq ss (entsel "Выберите компоновку или её элемент."))
    (if (cp:part-id (car ss)) (cp:parts-pick (car ss))
      (progn
        (setq ob (vlax-ename->vla-object (car ss)))
        (if (and (= (vla-get-objectname ob) "AcDbBlockReference")
                 (assoc -3 (entget (car ss) (list cp:app))) (setq cfg (vlax-ldata-get ob "settings")))
          (list ob cfg (cp:block-frame ob))
          (progn (princ "Это не компоновка, созданная CPDRAW.") nil))))))
(defun cp:run (update edit / *error* pick old new staged frame point undo path ready cp:failure)
  (defun *error* (msg)
    (cp:close-book) (cp:lib-close)
    (if (null new) (cp:cleanup-new))
    (if undo (vl-catch-all-apply 'vla-endundomark (list cp:doc)))
    (if (and (not cp:failure) (not (member msg '("Function cancelled" "quit / exit abort")))) (princ (strcat "\nCPDRAW: " msg)))
    (princ))
  (setq cp:doc (vla-get-activedocument (vlax-get-acad-object)) cp:newdef nil cp:measure-cache nil cp:pendingnew nil cp:pendingparts nil cp:pendinggroup nil)
  (if update
    (progn
      (if (null (setq pick (cp:pick))) (exit))
      (setq old (car pick) cp:cfg (cadr pick) frame (caddr pick) point (car frame)))
    (setq cp:cfg (cp:defaults)))
  (setq path (cp:g 'path))
  (if (or (null path) (not (findfile path))) (setq path (getfiled "Excel с однолинейкой" "" "xlsx;xlsm;xls" 0)))
  (if (null path) (exit))
  (cp:put 'path path) (cp:read-book path)
  (if (null cp:panels) (cp:fail "В однолинейке нет щитов."))
  (if (and update (not edit) (not (member (cp:g 'panel) cp:panels))) (cp:fail "Сохранённый щит не найден в Excel. Используйте CPEDIT для выбора другого щита."))
  (cp:import-library)
  (if (and edit (not (cp:dialog))) (exit))
  (setq ready nil)
  (while (not ready)
    (cp:import-library)
    (cp:collect (cp:g 'panel)) (cp:apply-sizes)
    (if (or edit (vl-some '(lambda (d) (null (nth 7 d))) cp:devices))
      (if (not (cp:sizes-dialog)) (exit)))
    (if (cp:plan) (setq ready T)
      (progn (alert cp:problem) (if (not (cp:dialog)) (exit)))))
  (if (not update)
    (progn
      (setq point (getpoint "Укажите точку вставки компоновки аппаратов: "))
      (if (null point) (exit))
      (setq point (trans point 1 0))))
  (vla-startundomark cp:doc) (setq undo T)
  (setq staged (cp:build point))
  (if frame
    (progn
      (vla-put-xscalefactor staged (nth 1 frame)) (vla-put-yscalefactor staged (nth 2 frame))
      (vla-put-zscalefactor staged (nth 3 frame)) (vla-put-rotation staged (nth 4 frame))))
  (if (and (assoc 'oneblock cp:cfg) (not (cp:g 'oneblock)))
    (setq staged (cp:separate staged (cp:block-frame staged))))
  (if old (cp:container-delete old))
  (setq new staged cp:pendingparts nil cp:pendinggroup nil cp:pendingnew nil)
  (vlax-ldata-put "SX_PANEL" "last" cp:cfg)
  (vla-endundomark cp:doc) (setq undo nil)
  (cp:lib-close) (vla-regen cp:doc 1)
  (princ (strcat "\nКомпоновка построена: " (cp:g 'panel) ", аппаратов " (itoa (length cp:devices)) ", клемм " (itoa (length cp:terminals)) "."))
  (princ))
(defun c:CPDRAW () (cp:run nil T))
(defun c:CPUPDATE () (cp:run T nil))
(defun c:CPEDIT () (cp:run T T))
(defun c:CPDELETE ( / pick doc)
  (if (setq pick (cp:pick))
    (progn (setq doc (vla-get-activedocument (vlax-get-acad-object)))
      (vla-startundomark doc) (cp:container-delete (car pick)) (vla-endundomark doc))) (princ))
(defun c:CPEXPLODE ( / *error* pick source result undo cp:failure)
  (defun *error* (msg)
    (if (null result) (cp:cleanup-new))
    (if undo (vl-catch-all-apply 'vla-endundomark (list cp:doc)))
    (if (and (not cp:failure) (not (member msg '("Function cancelled" "quit / exit abort")))) (princ (strcat "\nCPDRAW: " msg)))
    (princ))
  (setq cp:newdef nil cp:pendingnew nil cp:pendingparts nil cp:pendinggroup nil)
  (if (setq pick (cp:pick))
    (if (= (type (setq source (car pick))) 'LIST)
      (princ "Компоновка уже состоит из отдельных объектов.")
      (progn
        (setq cp:doc (vla-get-activedocument (vlax-get-acad-object)) cp:cfg (cadr pick))
        (cp:put 'oneblock nil)
        (vla-startundomark cp:doc) (setq undo T)
        (setq result (cp:separate source (caddr pick)) cp:pendingparts nil cp:pendinggroup nil)
        (vlax-ldata-put "SX_PANEL" "last" cp:cfg)
        (vla-endundomark cp:doc) (setq undo nil)
        (vla-regen cp:doc 1)
        (princ "Компоновка разделена на отдельные объекты."))))
  (princ))
(princ "\nSX_Panel v1.7: CPDRAW / CPUPDATE / CPEDIT / CPDELETE / CPEXPLODE")
(princ)
