(vl-load-com)
(if (= (getvar "DWGNAME") "Компоновка_проверка_из_базы.dwg")
(progn
(setq ppdoc (vla-get-activedocument (vlax-get-acad-object)) ppms (vla-get-modelspace ppdoc) ppf (open "C:/Users/user/Desktop/02_Справочники_CAD_Revit/odnolineyka/_Разработка/2026-10-09_panel-layout/actual_library_metrics.txt" "w") ppi 0)
(foreach name '("S201" "S203" "DS201" "VPR-2.5-3L-GY" "DIN_TH35_L500" "EKF_CM_2x7" "DKC_CQEN_1600x600x600_FRAME" "AV_2P_36" "AV_4P_72" "DA_4P_135" "SX_DYN_MCB")
  (setq x (* (rem ppi 5) 2000.0) y (* (fix (/ ppi 5)) -2000.0))
  (setq o (vla-insertblock ppms (vlax-3d-point (list x y 0.0)) name 1.0 1.0 1.0 0.0))
  (vla-getboundingbox o 'ppmn 'ppmx)
  (prin1 (list name (vlax-safearray->list ppmn) (vlax-safearray->list ppmx) (if (= (vla-get-isdynamicblock o) :vlax-true) (mapcar '(lambda (p) (list (vla-get-propertyname p) (vlax-variant-value (vla-get-value p)) (if (vlax-property-available-p p 'AllowedValues) (vlax-safearray->list (vlax-variant-value (vla-get-allowedvalues p)))))) (vlax-invoke o 'GetDynamicBlockProperties)))) ppf) (write-line "" ppf)
  (vla-addtext ppms name (vlax-3d-point (list x (- y 150.0) 0.0)) 14.0)
  (setq ppi (1+ ppi)))
(close ppf) (vla-regen ppdoc 1))) (princ)
