(vl-load-com)
(setq cppr:f (open "C:/Users/user/Desktop/02_Справочники_CAD_Revit/odnolineyka/_Разработка/2026-10-09_panel-layout/startup_probe.txt" "w"))
(foreach key '(cp:version cp:cfg cp:libpath cp:libsrc cp:devices)
 (prin1 (list key (if (= key 'cp:devices) (length cp:devices) (eval key))) cppr:f) (write-line "" cppr:f))
(prin1 (list 'source (findfile "SX_Panel.lsp") 'dcl (findfile "SX_Panel.dcl") 'saved-dcl (getenv "CP_DclFile") 'book (getenv "SX_LastXls") 'panel (getenv "SX_LastPanel")) cppr:f)
(write-line "" cppr:f)
(setq cppr:r (vl-catch-all-apply 'cp:dialog nil))
(prin1 (list 'dialog-result (if (vl-catch-all-error-p cppr:r) (vl-catch-all-error-message cppr:r) cppr:r)) cppr:f)
(close cppr:f) (princ)
