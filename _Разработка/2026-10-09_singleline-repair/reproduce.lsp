(vl-load-com)
(if (= (getvar "DWGNAME") "Однолинейка_проверка.dwg") (progn
(load "C:/Users/user/Desktop/02_Справочники_CAD_Revit/odnolineyka/2_AutoCAD/Однолинейка/SX_Schema.lsp")
(setq rpf (open "C:/Users/user/Desktop/02_Справочники_CAD_Revit/odnolineyka/_Разработка/2026-10-09_singleline-repair/reproduce.txt" "w") rpstage "init")
(vlax-ldata-put "SX_Schema" "xls" "\\\\Server\\DropBox\\Работа server\\4. Техдепартамент\\4.1. Проекты\\098 Ташкент-КТ\\5 ПИР\\5.4_Том 3 ХБК\\02_ELD-D1-02-ЭОМ\\Таблицы\\Однолинейка ЩC-ВК.02.xlsx")
(vlax-ldata-put "SX_Schema" "panel" "ЩC-ВК.02")
(vlax-ldata-put "SX_Schema" "sheet" "Однолинейка")
(vlax-ldata-put "SX_Schema" "pt" '(0.0 0.0 0.0))
(vlax-ldata-put "SX_Schema" "lib" "C:/missing.dwg")
(setq rpresult (vl-catch-all-apply 'sx:main (list T)))
(prin1 (list rpstage rptag (if (vl-catch-all-error-p rpresult) (vl-catch-all-error-message rpresult)) sx:errs sx:logl) rpf) (write-line "" rpf)
(setq rpcount 0 rptagged 0)
(vlax-for rpob sx:ms
  (if (and (= (vla-get-objectname rpob) "AcDbBlockReference") (= (vla-get-effectivename rpob) "SX_TCOL"))
    (progn
      (setq rpcount (1+ rpcount))
      (if (sx:xd-get (vlax-vla-object->ename rpob)) (setq rptagged (1+ rptagged))))))
(prin1 (list 'version sx:ver 'columns rpcount 'tagged rptagged 'invalid-ename-protected (vl-catch-all-error-p (sx:xd-set nil "TEST"))) rpf)
(vla-save sx:doc)
(close rpf))) (princ)
