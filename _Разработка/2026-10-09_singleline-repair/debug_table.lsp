(vl-load-com)
(if (= (getvar "DWGNAME") "Однолинейка_проверка.dwg") (progn
(load "C:/Users/user/Desktop/02_Справочники_CAD_Revit/odnolineyka/2_AutoCAD/Однолинейка/SX_Schema.lsp")
(setq rpf (open "C:/Users/user/Desktop/02_Справочники_CAD_Revit/odnolineyka/_Разработка/2026-10-09_singleline-repair/debug_table.txt" "w") rpstage "init")
(defun *error* (msg) (prin1 (list rpstage msg) rpf) (close rpf) (princ))
(setq sx:doc (vla-get-activedocument (vlax-get-acad-object)) sx:ms (vla-get-modelspace sx:doc)
      sx:P0 '(0.0 0.0 0.0) sx:R '(1.0 0.0) sx:D '(0.0 1.0) sx:ang 0.0 sx:tagpanel "TEST")
(sx:layers) (sx:roles) (setq sx:style (sx:ensure-style)) (sx:make-blocks T)
(setq rpstage "head block") (prin1 (list sx:bHEAD (sx:blk-p sx:bHEAD)) rpf) (write-line "" rpf)
(setq rpmark (entlast))
(setq rpstage "head insert") (setq rpob (sx:insv sx:bHEAD sx:vHeadDx 0.0 1.0 0.0 nil sx:TB))
(write-line "head inserted" rpf)
(setq rpstage "tagging") (sx:tag-new rpmark "H")
(write-line "head tagged" rpf)
(setq rpstage "column insert") (setq rpob (sx:ins "SX_TCOL" 10.0 0.0 '(("NAME1" . "TEST") ("CUR" . "10")) sx:TB))
(write-line "column inserted" rpf)
(close rpf))) (princ)
