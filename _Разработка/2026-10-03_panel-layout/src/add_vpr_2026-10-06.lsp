(setvar "CMDECHO" 0)
(setvar "OSMODE" 0)
(setvar "ATTREQ" 0)
(setq dir "C:/Users/marat/AppData/Local/Temp/claude/C--Users-marat-Desktop-SX------------/9b70fd8b-8c16-431e-8972-6668244a1be4/scratchpad/")
(defun cell (x0 y0 x1 y1)
  (entmake (list '(0 . "LWPOLYLINE") '(100 . "AcDbEntity") '(8 . "0") '(100 . "AcDbPolyline")
                 '(90 . 4) '(70 . 1) (list 10 x0 y1) (list 10 x1 y1) (list 10 x1 y0) (list 10 x0 y0))))
(defun cap (s x y)
  (entmake (list '(0 . "MTEXT") '(100 . "AcDbEntity") '(8 . "0") '(100 . "AcDbMText")
                 (list 10 x y 0.0) '(40 . 10.0) '(41 . 0.0) '(71 . 2) '(72 . 1) (cons 1 s) '(7 . "Standard"))))
(defun ins (name x y)
  (entmake (list '(0 . "INSERT") '(100 . "AcDbEntity") '(8 . "0") '(100 . "AcDbBlockReference")
                 (cons 2 name) (list 10 x y 0.0) '(41 . 1.0) '(42 . 1.0) '(43 . 1.0) '(50 . 0.0))))
(setq rail nil ss (ssget "X" '((0 . "INSERT"))) i 0)
(while (< i (sslength ss))
  (setq e (ssname ss i) p (cdr (assoc 10 (entget e))))
  (if (and (equal (car p) 2527.543 0.01) (equal (cadr p) 1123.4896 0.01)) (setq rail e))
  (setq i (1+ i)))
(if (null rail) (princ "
RAIL-NOT-FOUND
"))
(command "_.-INSERT" (strcat "VPRTMP=" dir "DKC_VPR_push-in.dwg") (list -5000.0 -5000.0) 1 1 0)
(setq mark (entlast))
(command "_.EXPLODE" mark)
(setq e (entnext mark))
(while e (setq nx (entnext e)) (entdel e) (setq e nx))
(command "_.-PURGE" "_B" "VPRTMP" "_N")
(command "_.-INSERT" (strcat "VPR-2.5-3L-GY=" dir "vpr3l_raw.dwg") (list -5000.0 -5000.0) 1 1 0)
(entdel (entlast))
(command "_.COPY" rail "" (list 2527.54323342981 1123.489645820265) (list 2527.54323342981 500.290000))
(cell 2517.400 417.600 2634.600 573.400)
(cap "VPR-1.5" 2576.000 567.400)
(ins "VPR-1.5-GY" 2561.900 500.290000)
(ins "VPR-1.5-BU" 2568.400 500.290000)
(ins "VPR-1.5-OR" 2574.900 500.290000)
(ins "VPR-1.5-PE" 2581.400 500.290000)
(ins "D-VPR-1.5" 2587.900 500.290000)
(cell 2634.600 417.600 2751.800 573.400)
(cap "VPR-1.5-TWIN" 2693.200 567.400)
(ins "VPR-1.5-TWIN-GY" 2679.100 500.290000)
(ins "VPR-1.5-TWIN-BU" 2685.600 500.290000)
(ins "VPR-1.5-TWIN-OR" 2692.100 500.290000)
(ins "VPR-1.5-TWIN-PE" 2698.600 500.290000)
(ins "D-VPR-1.5-TWIN" 2705.100 500.290000)
(cell 2751.800 417.600 2869.000 573.400)
(cap "VPR-1.5-QUATTRO" 2810.400 567.400)
(ins "VPR-1.5-QUATTRO-GY" 2799.550 500.290000)
(ins "VPR-1.5-QUATTRO-OR" 2806.050 500.290000)
(ins "VPR-1.5-QUATTRO-PE" 2812.550 500.290000)
(ins "D-VPR-1.5-QUATTRO" 2819.050 500.290000)
(cell 2869.000 417.600 2986.200 573.400)
(cap "VPR-2.5" 2927.600 567.400)
(ins "VPR-2.5-GY" 2914.200 500.290000)
(ins "VPR-2.5-BU" 2922.400 500.290000)
(ins "VPR-2.5-PE-YG" 2930.600 500.290000)
(ins "D-VPR-2.5" 2938.800 500.290000)
(cell 2986.200 417.600 3103.400 573.400)
(cap "VPR-2.5-TWIN" 3044.800 567.400)
(ins "VPR-2.5-TWIN-GY" 3031.400 500.290000)
(ins "VPR-2.5-TWIN-BU" 3039.600 500.290000)
(ins "VPR-2.5-TWIN-PE-YG" 3047.800 500.290000)
(ins "D-VPR-2.5-TWIN" 3056.000 500.290000)
(cell 3103.400 417.600 3220.600 573.400)
(cap "VPR-2.5-QUATTRO" 3162.000 567.400)
(ins "VPR-2.5-QUATTRO-GY" 3148.600 500.290000)
(ins "VPR-2.5-QUATTRO-BU" 3156.800 500.290000)
(ins "VPR-2.5-QUATTRO-PE" 3165.000 500.290000)
(ins "D-VPR-2.5-QUATTRO" 3173.200 500.290000)
(cell 3220.600 417.600 3337.800 573.400)
(cap "VPR-4" 3279.200 567.400)
(ins "VPR-4-GY" 3264.300 500.290000)
(ins "VPR-4-BU" 3273.500 500.290000)
(ins "VPR-4-PE-YG" 3282.700 500.290000)
(ins "D-VPR-4" 3291.900 500.290000)
(command "_.COPY" rail "" (list 2527.54323342981 1123.489645820265) (list 2527.54323342981 344.490000))
(cell 2517.400 261.800 2634.600 417.600)
(cap "VPR-4-TWIN" 2576.000 411.600)
(ins "VPR-4-TWIN-GY" 2561.100 344.490000)
(ins "VPR-4-TWIN-BU" 2570.300 344.490000)
(ins "VPR-4-TWIN-PE-YG" 2579.500 344.490000)
(ins "D-VPR-4-TWIN" 2588.700 344.490000)
(cell 2634.600 261.800 2751.800 417.600)
(cap "VPR-4-QUATTRO" 2693.200 411.600)
(ins "VPR-4-QUATTRO-GY" 2678.300 344.490000)
(ins "VPR-4-QUATTRO-BU" 2687.500 344.490000)
(ins "VPR-4-QUATTRO-PE" 2696.700 344.490000)
(ins "D-VPR-4-QUATTRO" 2705.900 344.490000)
(cell 2751.800 261.800 2869.000 417.600)
(cap "VPR-6" 2810.400 411.600)
(ins "VPR-6-GY" 2792.500 344.490000)
(ins "VPR-6-BU" 2803.700 344.490000)
(ins "VPR-6-PE-YG" 2814.900 344.490000)
(ins "D-VPR-6" 2826.100 344.490000)
(cell 2869.000 261.800 2986.200 417.600)
(cap "VPR-6-TWIN" 2927.600 411.600)
(ins "VPR-6-TWIN-GY" 2920.900 344.490000)
(ins "D-VPR-6-TWIN" 2932.100 344.490000)
(cell 2986.200 261.800 3103.400 417.600)
(cap "VPR-10" 3044.800 411.600)
(ins "VPR-10-GY" 3023.900 344.490000)
(ins "VPR-10-BU" 3037.100 344.490000)
(ins "VPR-10-PE-YG" 3050.300 344.490000)
(ins "D-VPR-10" 3063.500 344.490000)
(cell 3103.400 261.800 3220.600 417.600)
(cap "VPR-10-TWIN" 3162.000 411.600)
(ins "VPR-10-TWIN-GY" 3154.300 344.490000)
(ins "D-VPR-10-TWIN" 3167.500 344.490000)
(cell 3220.600 261.800 3337.800 417.600)
(cap "VPR-16" 3279.200 411.600)
(ins "VPR-16-GY" 3255.300 344.490000)
(ins "VPR-16-BU" 3270.500 344.490000)
(ins "VPR-16-PE-YG" 3285.700 344.490000)
(ins "D-VPR-16" 3300.900 344.490000)
(command "_.COPY" rail "" (list 2527.54323342981 1123.489645820265) (list 2527.54323342981 188.690000))
(cell 2517.400 106.000 2634.600 261.800)
(cap "VPR-16-TWIN" 2576.000 255.800)
(ins "VPR-16-TWIN-GY" 2567.300 188.690000)
(ins "D-VPR-16-TWIN" 2582.500 188.690000)
(cell 2634.600 106.000 2751.800 261.800)
(cap "VPR-2.5-3L" 2693.200 255.800)
(ins "VPR-2.5-3L-GY" 2671.600 188.690000)
(ins "VPR-2.5-3L-BU" 2679.800 188.690000)
(ins "VPR-2.5-3L-PE-YG" 2688.000 188.690000)
(ins "VPR-2.5-3L-PV-GY" 2696.200 188.690000)
(ins "VPR-2.5-3L-PV-BU" 2704.400 188.690000)
(ins "D-VPR-2.5-3L" 2712.600 188.690000)
(command "_.AUDIT" "_Y")
(command "_.ZOOM" "_E")
(princ "
ADD-VPR-DONE
")
(princ)
