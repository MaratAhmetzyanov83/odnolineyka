;;; Пополнение «База блоков компоновки.dwg»: Arlight — блоки питания на DIN-рейку и 4-канальные диммеры.
;;; Сгенерировано src/make_arlight.py (режим lsp). Ряды под низом базы (T0), рейка — копия «Дин.рейка» ряда VPR.
(setvar "CMDECHO" 0)
(setvar "OSMODE" 0)
(setvar "ATTREQ" 0)
(defun cell (x0 y0 x1 y1)
  (entmake (list '(0 . "LWPOLYLINE") '(100 . "AcDbEntity") '(8 . "0") '(100 . "AcDbPolyline")
                 '(90 . 4) '(70 . 1) (list 10 x0 y1) (list 10 x1 y1) (list 10 x1 y0) (list 10 x0 y0))))
(defun cap (s x y w)
  (entmake (list '(0 . "MTEXT") '(100 . "AcDbEntity") '(8 . "0") '(100 . "AcDbMText")
                 (list 10 x y 0.0) '(40 . 5.0) (cons 41 w) '(71 . 2) '(72 . 1) (cons 1 s) '(7 . "Standard"))))
(defun ins (name x y)
  (entmake (list '(0 . "INSERT") '(100 . "AcDbEntity") '(8 . "0") '(100 . "AcDbBlockReference")
                 (cons 2 name) (list 10 x y 0.0) '(41 . 1.0) '(42 . 1.0) '(43 . 1.0) '(50 . 0.0))))
(setq rail nil ss (ssget "X" '((0 . "INSERT"))) i 0)
(while (< i (sslength ss))
  (setq e (ssname ss i) p (cdr (assoc 10 (entget e))))
  (if (and (equal (car p) 2527.543 0.01) (equal (cadr p) 1123.4896 0.01)) (setq rail e))
  (setq i (1+ i)))
(if (null rail) (princ "\nRAIL-NOT-FOUND\n"))
;; верх новых рядов — низ чертежа минус 20 (базу дополняют и другие наборы)
(command "_.ZOOM" "_E")
(setq T0 (- (cadr (getvar "EXTMIN")) 20.0))
(defun Y (d) (+ T0 d))
;; блоки из Arlight_DIN.dwg: вставить, расчленить один раз, лист-каталог удалить
(command "_.-INSERT" "ALTMP=C:/Users/marat/AppData/Local/Temp/claude/C--Users-marat-Desktop-SX------------/a0da9f5d-29c7-4d5c-86bc-b8e89476221d/scratchpad/al/Arlight_DIN.dwg" (list -5000.0 -5000.0) 1 1 0)
(setq mark (entlast))
(command "_.EXPLODE" mark)
(setq e (entnext mark))
(while e (setq nx (entnext e)) (entdel e) (setq e nx))
(command "_.-PURGE" "_B" "ALTMP" "_N")
(command "_.COPY" rail "" (list 2527.54323342981 1123.489645820265) (list 2527.54323342981 (Y -73.1100)))
(cell 2517.400 (Y -155.800) 2634.600 (Y 0.000))
(cap "ARV-DR15-12" 2576.000 (Y -3.000) 113.2)
(ins "ARV-DR15-12" 2567.250 (Y -73.1100))
(cell 2634.600 (Y -155.800) 2751.800 (Y 0.000))
(cap "ARV-DR30-12" 2693.200 (Y -3.000) 113.2)
(ins "ARV-DR30-12" 2675.700 (Y -73.1100))
(cell 2751.800 (Y -155.800) 2869.000 (Y 0.000))
(cap "ARV-DR60-12" 2810.400 (Y -3.000) 113.2)
(ins "ARV-DR60-12" 2784.150 (Y -73.1100))
(cell 2869.000 (Y -155.800) 2986.200 (Y 0.000))
(cap "ARV-DR100-12" 2927.600 (Y -3.000) 113.2)
(ins "ARV-DR100-12" 2892.600 (Y -73.1100))
(cell 2986.200 (Y -155.800) 3142.200 (Y 0.000))
(cap "ARV-DR135-12" 3064.200 (Y -3.000) 152.0)
(ins "ARV-DR135-12" 3011.700 (Y -73.1100))
(command "_.COPY" rail "" (list 2527.54323342981 1123.489645820265) (list 2527.54323342981 (Y -228.9100)))
(cell 2517.400 (Y -311.600) 2634.600 (Y -155.800))
(cap "ARV-DR15-24" 2576.000 (Y -158.800) 113.2)
(ins "ARV-DR15-24" 2567.250 (Y -228.9100))
(cell 2634.600 (Y -311.600) 2751.800 (Y -155.800))
(cap "ARV-DR30-24" 2693.200 (Y -158.800) 113.2)
(ins "ARV-DR30-24" 2675.700 (Y -228.9100))
(cell 2751.800 (Y -311.600) 2869.000 (Y -155.800))
(cap "ARV-DR60-24" 2810.400 (Y -158.800) 113.2)
(ins "ARV-DR60-24" 2784.150 (Y -228.9100))
(cell 2869.000 (Y -311.600) 2986.200 (Y -155.800))
(cap "ARV-DR100-24" 2927.600 (Y -158.800) 113.2)
(ins "ARV-DR100-24" 2892.600 (Y -228.9100))
(cell 2986.200 (Y -311.600) 3142.200 (Y -155.800))
(cap "ARV-DR150-24" 3064.200 (Y -158.800) 152.0)
(ins "ARV-DR150-24" 3011.700 (Y -228.9100))
(command "_.COPY" rail "" (list 2527.54323342981 1123.489645820265) (list 2527.54323342981 (Y -384.7100)))
(cell 2517.400 (Y -467.400) 2634.600 (Y -311.600))
(cap "ARV-DR15-48" 2576.000 (Y -314.600) 113.2)
(ins "ARV-DR15-48" 2567.250 (Y -384.7100))
(cell 2634.600 (Y -467.400) 2751.800 (Y -311.600))
(cap "ARV-DR30-48" 2693.200 (Y -314.600) 113.2)
(ins "ARV-DR30-48" 2675.700 (Y -384.7100))
(cell 2751.800 (Y -467.400) 2869.000 (Y -311.600))
(cap "ARV-DR60-48" 2810.400 (Y -314.600) 113.2)
(ins "ARV-DR60-48" 2784.150 (Y -384.7100))
(cell 2869.000 (Y -467.400) 2986.200 (Y -311.600))
(cap "ARV-DR100-48" 2927.600 (Y -314.600) 113.2)
(ins "ARV-DR100-48" 2892.600 (Y -384.7100))
(cell 2986.200 (Y -467.400) 3142.200 (Y -311.600))
(cap "ARV-DR150-48" 3064.200 (Y -314.600) 152.0)
(ins "ARV-DR150-48" 3011.700 (Y -384.7100))
(command "_.COPY" rail "" (list 2527.54323342981 1123.489645820265) (list 2527.54323342981 (Y -540.5100)))
(cell 2517.400 (Y -623.200) 2634.600 (Y -467.400))
(cap "ARV-DRS-15-24" 2576.000 (Y -470.400) 113.2)
(ins "ARV-DRS-15-24" 2567.250 (Y -540.5100))
(cell 2634.600 (Y -623.200) 2751.800 (Y -467.400))
(cap "ARV-DRS-36-24" 2693.200 (Y -470.400) 113.2)
(ins "ARV-DRS-36-24" 2675.700 (Y -540.5100))
(cell 2751.800 (Y -623.200) 2869.000 (Y -467.400))
(cap "ARV-DRS-60-24" 2810.400 (Y -470.400) 113.2)
(ins "ARV-DRS-60-24" 2784.150 (Y -540.5100))
(cell 2869.000 (Y -623.200) 2986.200 (Y -467.400))
(cap "ARV-DRS-100-24" 2927.600 (Y -470.400) 113.2)
(ins "ARV-DRS-100-24" 2892.600 (Y -540.5100))
(cell 2986.200 (Y -623.200) 3142.200 (Y -467.400))
(cap "ARV-DRS-150-24" 3064.200 (Y -470.400) 152.0)
(ins "ARV-DRS-150-24" 3011.700 (Y -540.5100))
(command "_.COPY" rail "" (list 2527.54323342981 1123.489645820265) (list 2527.54323342981 (Y -723.2000)))
(cell 2517.400 (Y -823.200) 2634.600 (Y -623.200))
(cap "ARV-DRP75-24" 2576.000 (Y -626.200) 113.2)
(ins "ARV-DRP75-24" 2555.000 (Y -723.2000))
(cell 2634.600 (Y -823.200) 2751.800 (Y -623.200))
(cap "ARV-DRP120-24-B" 2693.200 (Y -626.200) 113.2)
(ins "ARV-DRP120-24-B" 2672.200 (Y -723.2000))
(cell 2751.800 (Y -823.200) 2869.000 (Y -623.200))
(cap "ARV-DRP240-24-B" 2810.400 (Y -626.200) 113.2)
(ins "ARV-DRP240-24-B" 2778.900 (Y -723.2000))
(cell 2869.000 (Y -823.200) 2986.200 (Y -623.200))
(cap "ARV-DRP480-PFC-24" 2927.600 (Y -626.200) 113.2)
(ins "ARV-DRP480-PFC-24" 2885.600 (Y -723.2000))
(cell 2986.200 (Y -823.200) 3142.200 (Y -623.200))
(cap "ARV-DRP960-24" 3064.200 (Y -626.200) 152.0)
(ins "ARV-DRP960-24" 2989.200 (Y -723.2000))
(command "_.COPY" rail "" (list 2527.54323342981 1123.489645820265) (list 2527.54323342981 (Y -923.2000)))
(cell 2517.400 (Y -1023.200) 2634.600 (Y -823.200))
(cap "ARV-DRP75-48" 2576.000 (Y -826.200) 113.2)
(ins "ARV-DRP75-48" 2555.000 (Y -923.2000))
(cell 2634.600 (Y -1023.200) 2751.800 (Y -823.200))
(cap "ARV-DRP120-48-B" 2693.200 (Y -826.200) 113.2)
(ins "ARV-DRP120-48-B" 2672.200 (Y -923.2000))
(cell 2751.800 (Y -1023.200) 2869.000 (Y -823.200))
(cap "ARV-DRP240-PFC-48" 2810.400 (Y -826.200) 113.2)
(ins "ARV-DRP240-PFC-48" 2778.900 (Y -923.2000))
(cell 2869.000 (Y -1023.200) 2986.200 (Y -823.200))
(cap "ARV-DRP480-PFC-48" 2927.600 (Y -826.200) 113.2)
(ins "ARV-DRP480-PFC-48" 2885.600 (Y -923.2000))
(command "_.COPY" rail "" (list 2527.54323342981 1123.489645820265) (list 2527.54323342981 (Y -1123.2000)))
(cell 2517.400 (Y -1223.200) 2634.600 (Y -1023.200))
(cap "ARV-DRP75-24-Y" 2576.000 (Y -1026.200) 113.2)
(ins "ARV-DRP75-24-Y" 2560.500 (Y -1123.2000))
(cell 2634.600 (Y -1223.200) 2751.800 (Y -1023.200))
(cap "ARV-DRP120-24-Y" 2693.200 (Y -1026.200) 113.2)
(ins "ARV-DRP120-24-Y" 2677.700 (Y -1123.2000))
(cell 2751.800 (Y -1223.200) 2869.000 (Y -1023.200))
(cap "ARV-DRP240-24-PFC-Y" 2810.400 (Y -1026.200) 113.2)
(ins "ARV-DRP240-24-PFC-Y" 2789.900 (Y -1123.2000))
(cell 2869.000 (Y -1223.200) 2986.200 (Y -1023.200))
(cap "ARV-DRP480-24-PFC-Y" 2927.600 (Y -1026.200) 113.2)
(ins "ARV-DRP480-24-PFC-Y" 2902.100 (Y -1123.2000))
(command "_.COPY" rail "" (list 2527.54323342981 1123.489645820265) (list 2527.54323342981 (Y -1296.3100)))
(cell 2517.400 (Y -1379.000) 2634.600 (Y -1223.200))
(cap "KNX-104-DIM-DIN" 2576.000 (Y -1226.200) 113.2)
(ins "KNX-104-DIM-DIN" 2540.000 (Y -1296.3100))
(cell 2634.600 (Y -1379.000) 2751.800 (Y -1223.200))
(cap "KNX-204-DIM-DIN" 2693.200 (Y -1226.200) 113.2)
(ins "KNX-204-DIM-DIN" 2657.200 (Y -1296.3100))
(cell 2751.800 (Y -1379.000) 2869.000 (Y -1223.200))
(cap "SR-KN041CC-DIN" 2810.400 (Y -1226.200) 113.2)
(ins "SR-KN041CC-DIN" 2774.400 (Y -1296.3100))
(cell 2869.000 (Y -1379.000) 3025.000 (Y -1223.200))
(cap "DALI-504-TE-DIN" 2947.000 (Y -1226.200) 152.0)
(ins "DALI-504-TE-DIN" 2874.500 (Y -1296.3100))
(cell 3025.000 (Y -1379.000) 3181.000 (Y -1223.200))
(cap "SMART-DALI-104-82-\\PRGBW-DT6-DT8-RDM-DIN" 3103.000 (Y -1226.200) 152.0)
(ins "SMART-DALI-104-82-RGBW-DT6-DT8-RDM-DIN" 3045.500 (Y -1296.3100))
(cell 3181.000 (Y -1379.000) 3298.200 (Y -1223.200))
(cap "SR-2303DIN-PD" 3239.600 (Y -1226.200) 113.2)
(ins "SR-2303DIN-PD" 3207.100 (Y -1296.3100))
(cell 3298.200 (Y -1379.000) 3415.400 (Y -1223.200))
(cap "SR-2108FA-RJ45-DIN" 3356.800 (Y -1226.200) 113.2)
(ins "SR-2108FA-RJ45-DIN" 3324.300 (Y -1296.3100))
(command "_.COPY" rail "" (list 2527.54323342981 1123.489645820265) (list 2527.54323342981 (Y -1452.1100)))
(cell 2517.400 (Y -1534.800) 2673.400 (Y -1379.000))
(cap "SMART-D23-DIM-PUSH-DIN" 2595.400 (Y -1382.000) 152.0)
(ins "SMART-D23-DIM-PUSH-DIN" 2540.400 (Y -1452.1100))
(cell 2673.400 (Y -1534.800) 2829.400 (Y -1379.000))
(cap "SMART-DALI-104-62-ADDR-\\PDIM-DT6-DIN White" 2751.400 (Y -1382.000) 152.0)
(ins "SMART-DALI-104-62-ADDR-DIM-DT6-DIN White" 2696.400 (Y -1452.1100))
(cell 2829.400 (Y -1534.800) 2985.400 (Y -1379.000))
(cap "SMART-DALI-104-62-ADDR-\\PDIM-DT6-DIN Black" 2907.400 (Y -1382.000) 152.0)
(ins "SMART-DALI-104-62-ADDR-DIM-DT6-DIN Black" 2852.400 (Y -1452.1100))
(cell 2985.400 (Y -1534.800) 3141.400 (Y -1379.000))
(cap "SMART-DALI-104-62-ADDR-\\PRGBW-DT6-DT8-PD-DIN White" 3063.400 (Y -1382.000) 152.0)
(ins "SMART-DALI-104-62-ADDR-RGBW-DT6-DT8-PD-DIN White" 3008.400 (Y -1452.1100))
(cell 3141.400 (Y -1534.800) 3297.400 (Y -1379.000))
(cap "SMART-DALI-104-62-ADDR-\\PRGBW-DT6-DT8-PD-DIN Black" 3219.400 (Y -1382.000) 152.0)
(ins "SMART-DALI-104-62-ADDR-RGBW-DT6-DT8-PD-DIN Black" 3164.400 (Y -1452.1100))
(command "_.COPY" rail "" (list 2527.54323342981 1123.489645820265) (list 2527.54323342981 (Y -1607.9100)))
(cell 2517.400 (Y -1690.600) 2673.400 (Y -1534.800))
(cap "SMART-K3-RGBW" 2595.400 (Y -1537.800) 152.0)
(ins "SMART-K3-RGBW" 2537.900 (Y -1607.9100))
(cell 2673.400 (Y -1690.600) 2829.400 (Y -1534.800))
(cap "SMART-K36-DMX" 2751.400 (Y -1537.800) 152.0)
(ins "SMART-K36-DMX" 2696.400 (Y -1607.9100))
(cell 2829.400 (Y -1690.600) 2985.400 (Y -1534.800))
(cap "SMART-RGBW-DIN" 2907.400 (Y -1537.800) 152.0)
(ins "SMART-RGBW-DIN" 2849.900 (Y -1607.9100))
(command "_.AUDIT" "_Y")
(command "_.ZOOM" "_E")
(princ "\nADD-ARLIGHT-DONE\n")
(princ)
