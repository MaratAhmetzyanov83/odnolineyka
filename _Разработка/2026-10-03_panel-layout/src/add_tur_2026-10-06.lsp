(setvar "CMDECHO" 0)
(setvar "OSMODE" 0)
(setvar "ATTREQ" 0)
(defun cell (x0 y0 x1 y1)
  (entmake (list '(0 . "LWPOLYLINE") '(100 . "AcDbEntity") '(8 . "0") '(100 . "AcDbPolyline")
                 '(90 . 4) '(70 . 1) (list 10 x0 y1) (list 10 x1 y1) (list 10 x1 y0) (list 10 x0 y0))))
(defun cap (s x y h)
  (entmake (list '(0 . "MTEXT") '(100 . "AcDbEntity") '(8 . "0") '(100 . "AcDbMText")
                 (list 10 x y 0.0) (cons 40 h) '(41 . 0.0) '(71 . 2) '(72 . 1) (cons 1 s) '(7 . "Standard"))))
(defun ins (name x y)
  (entmake (list '(0 . "INSERT") '(100 . "AcDbEntity") '(8 . "0") '(100 . "AcDbBlockReference")
                 (cons 2 name) (list 10 x y 0.0) '(41 . 1.0) '(42 . 1.0) '(43 . 1.0) '(50 . 0.0))))
(setq rail nil ss (ssget "X" '((0 . "INSERT"))) i 0)
(while (< i (sslength ss))
  (setq e (ssname ss i) p (cdr (assoc 10 (entget e))))
  (if (and (equal (car p) 2527.543 0.01) (equal (cadr p) 1123.4896 0.01)) (setq rail e))
  (setq i (1+ i)))
(if (null rail) (princ "
RAIL-NOT-FOUND
"))
(command "_.-INSERT" "TURTMP=C:/Users/marat/AppData/Local/Temp/claude/C--Users-marat-Desktop-SX------------/9b70fd8b-8c16-431e-8972-6668244a1be4/scratchpad/DKC_TUR_screw.dwg" (list -5000.0 -5000.0) 1 1 0)
(setq mark (entlast))
(command "_.EXPLODE" mark)
(setq e (entnext mark))
(while e (setq nx (entnext e)) (entdel e) (setq e nx))
(command "_.-PURGE" "_B" "TURTMP" "_N")
(command "_.COPY" rail "" (list 2527.54323342981 1123.489645820265) (list 2527.54323342981 32.890000))
(cell 2517.400 -49.800 2634.600 106.000)
(cap "TUR-2.5" 2576.000 100.000 10.0)
(ins "TUR-2.5" 2562.600 32.890000)
(ins "TUR-2.5-BU" 2570.800 32.890000)
(ins "TUR-2.5-PE" 2579.000 32.890000)
(ins "D-TUR-2.5-10" 2587.200 32.890000)
(cell 2634.600 -49.800 2751.800 106.000)
(cap "TUR-4" 2693.200 100.000 10.0)
(ins "TUR-4" 2678.300 32.890000)
(ins "TUR-4-BU" 2687.500 32.890000)
(ins "TUR-4-PE" 2696.700 32.890000)
(ins "D-TUR-2.5-10" 2705.900 32.890000)
(cell 2751.800 -49.800 2869.000 106.000)
(cap "TUR-6" 2810.400 100.000 10.0)
(ins "TUR-6" 2792.500 32.890000)
(ins "TUR-6-BU" 2803.700 32.890000)
(ins "TUR-6-PE" 2814.900 32.890000)
(ins "D-TUR-2.5-10" 2826.100 32.890000)
(cell 2869.000 -49.800 2986.200 106.000)
(cap "TUR-10" 2927.600 100.000 10.0)
(ins "TUR-10" 2906.700 32.890000)
(ins "TUR-10-BU" 2919.900 32.890000)
(ins "TUR-10-PE" 2933.100 32.890000)
(ins "D-TUR-2.5-10" 2946.300 32.890000)
(cell 2986.200 -49.800 3103.400 106.000)
(cap "TUR-16" 3044.800 100.000 10.0)
(ins "TUR-16" 3026.100 32.890000)
(ins "TUR-16-BU" 3041.100 32.890000)
(ins "D-TUR-16" 3056.100 32.890000)
(ins "D-TUR-16R-BU" 3061.300 32.890000)
(cell 3103.400 -49.800 3220.600 106.000)
(cap "TUR-2.5-TWIN" 3162.000 100.000 10.0)
(ins "TUR-2.5-TWIN" 3152.700 32.890000)
(ins "TUR-2.5-TWIN-BU" 3160.900 32.890000)
(ins "D-TUR-2.5-TWIN" 3169.100 32.890000)
(cell 3220.600 -49.800 3337.800 106.000)
(cap "TUR-2.5-QUATTRO" 3279.200 100.000 8.0)
(ins "TUR-2.5-QUATTRO" 3269.900 32.890000)
(ins "TUR-2.5-QUATTRO-BU" 3278.100 32.890000)
(ins "D-TUR-2.5-QUATTRO" 3286.300 32.890000)
(command "_.COPY" rail "" (list 2527.54323342981 1123.489645820265) (list 2527.54323342981 -122.910000))
(cell 2517.400 -205.600 2634.600 -49.800)
(cap "TUR-4-TWIN" 2576.000 -55.800 10.0)
(ins "TUR-4-TWIN" 2565.700 -122.910000)
(ins "TUR-4-TWIN-BU" 2574.900 -122.910000)
(ins "D-TUR-4-TWIN" 2584.100 -122.910000)
(cell 2634.600 -205.600 2751.800 -49.800)
(cap "TUR-4-QUATTRO" 2693.200 -55.800 8.0)
(ins "TUR-4-QUATTRO" 2682.900 -122.910000)
(ins "TUR-4-QUATTRO-BU" 2692.100 -122.910000)
(ins "D-TUR-4-QUATTRO" 2701.300 -122.910000)
(cell 2751.800 -205.600 2869.000 -49.800)
(cap "TUR-2.5R" 2810.400 -55.800 10.0)
(ins "TUR-2.5R" 2778.000 -122.910000)
(ins "TUR-2.5R-BK" 2786.200 -122.910000)
(ins "TUR-2.5R-BU" 2794.400 -122.910000)
(ins "TUR-2.5R-GN" 2802.600 -122.910000)
(ins "TUR-2.5R-OR" 2810.800 -122.910000)
(ins "TUR-2.5R-RD" 2819.000 -122.910000)
(ins "TUR-2.5R-YE" 2827.200 -122.910000)
(ins "D-TUR-2.5-10R" 2835.400 -122.910000)
(ins "D-TUR-2.5-10R-BU" 2840.600 -122.910000)
(cell 2869.000 -205.600 2986.200 -49.800)
(cap "TUR-4R" 2927.600 -55.800 10.0)
(ins "TUR-4R" 2903.500 -122.910000)
(ins "TUR-4R-BU" 2912.700 -122.910000)
(ins "TUR-4R-OR" 2921.900 -122.910000)
(ins "TUR-4R-RD" 2931.100 -122.910000)
(ins "TUR-4R-YE" 2940.300 -122.910000)
(ins "D-TUR-2.5-10R" 2949.500 -122.910000)
(cell 2986.200 -205.600 3103.400 -49.800)
(cap "TUR-35R" 3044.800 -55.800 10.0)
(ins "TUR-35R" 3022.100 -122.910000)
(ins "TUR-35R-BU" 3041.100 -122.910000)
(ins "D-TUR-35R" 3060.100 -122.910000)
(ins "D-TUR-35R-BU" 3065.300 -122.910000)
(cell 3103.400 -205.600 3220.600 -49.800)
(cap "TUR-M" 3162.000 -55.800 10.0)
(ins "TUR-M-2.5" 3139.400 -122.910000)
(ins "TUR-M-2.5-BU" 3147.600 -122.910000)
(ins "TUR-M-2.5-PE" 3155.800 -122.910000)
(ins "TUR-M-4" 3164.000 -122.910000)
(ins "TUR-M-4-BU" 3173.200 -122.910000)
(ins "D-TUR-M-2.5-4" 3182.400 -122.910000)
(cell 3220.600 -205.600 3337.800 -49.800)
(cap "KRU-35N" 3279.200 -55.800 10.0)
(ins "KRU-35N" 3262.500 -122.910000)
(ins "KRU-35N-BU" 3280.700 -122.910000)
(command "_.COPY" rail "" (list 2527.54323342981 1123.489645820265) (list 2527.54323342981 -278.710000))
(cell 2517.400 -361.400 2634.600 -205.600)
(cap "KRUSLG" 2576.000 -211.600 10.0)
(ins "KRUSLG-16N" 2535.300 -278.710000)
(ins "KRUSLG-35N" 2550.500 -278.710000)
(ins "KRUSLG-50N" 2568.700 -278.710000)
(ins "KRUSLG-95N" 2591.700 -278.710000)
(cell 2634.600 -361.400 2751.800 -205.600)
(cap "KRUH-50" 2693.200 -211.600 10.0)
(ins "KRUH-50" 2671.700 -278.710000)
(ins "KRUH-50-BU" 2694.700 -278.710000)
(cell 2751.800 -361.400 2869.000 -205.600)
(cap "KRUH-95" 2810.400 -211.600 10.0)
(ins "KRUH-95" 2783.900 -278.710000)
(ins "KRUH-95-BU" 2811.900 -278.710000)
(cell 2869.000 -361.400 2986.200 -205.600)
(cap "KRUH-150" 2927.600 -211.600 10.0)
(ins "KRUH-150" 2895.100 -278.710000)
(ins "KRUH-150-BU" 2929.100 -278.710000)
(cell 2986.200 -361.400 3103.400 -205.600)
(cap "KRUH-240" 3044.800 -211.600 10.0)
(ins "KRUH-240" 3007.300 -278.710000)
(ins "KRUH-240-BU" 3046.300 -278.710000)
(cell 3103.400 -361.400 3220.600 -205.600)
(cap "TTURB-4" 3162.000 -211.600 10.0)
(ins "TTURB-4" 3151.700 -278.710000)
(ins "TTURB-4-BU" 3160.900 -278.710000)
(ins "D-TTURB-4" 3170.100 -278.710000)
(cell 3220.600 -361.400 3337.800 -205.600)
(cap "KRUK-3" 3279.200 -211.600 10.0)
(ins "KRUK-3" 3269.750 -278.710000)
(ins "KRUK-3-PV" 3277.950 -278.710000)
(ins "D-KRUK-3-5" 3286.150 -278.710000)
(command "_.COPY" rail "" (list 2527.54323342981 1123.489645820265) (list 2527.54323342981 -434.510000))
(cell 2517.400 -517.200 2634.600 -361.400)
(cap "KRUKB" 2576.000 -367.400 10.0)
(ins "KRUKB-3" 2548.150 -434.510000)
(ins "KRUKB-3-BU" 2556.350 -434.510000)
(ins "KRUKB-5" 2564.550 -434.510000)
(ins "KRUKB-5-BU" 2573.750 -434.510000)
(ins "KRUKB-5-PE" 2582.950 -434.510000)
(ins "KRUK-5-PV" 2592.150 -434.510000)
(ins "D-KRUKB-3-5" 2601.350 -434.510000)
(command "_.AUDIT" "_Y")
(command "_.ZOOM" "_E")
(princ "
ADD-TUR-DONE
")
(princ)
