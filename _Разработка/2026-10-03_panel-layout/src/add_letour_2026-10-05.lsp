(setvar "CMDECHO" 0)
(setvar "OSMODE" 0)
(setvar "ATTREQ" 0)
(setq dir "C:/Users/marat/AppData/Local/Temp/claude/C--Users-marat-Desktop-SX------------/9b70fd8b-8c16-431e-8972-6668244a1be4/scratchpad/")
(defun cell (x0 y0 x1 y1)
  (entmake (list '(0 . "LWPOLYLINE") '(100 . "AcDbEntity") '(8 . "0") '(100 . "AcDbPolyline")
                 '(90 . 4) '(70 . 1) (list 10 x0 y1) (list 10 x1 y1) (list 10 x1 y0) (list 10 x0 y0))))
(defun cap (s x y)
  (entmake (list '(0 . "MTEXT") '(100 . "AcDbEntity") '(8 . "0") '(100 . "AcDbMText")
                 (list 10 x y 0.0) '(40 . 10.0) '(41 . 0.0) '(71 . 2) '(72 . 1) (cons 1 s) '(7 . "Standard"))))
(setq rail nil ss (ssget "X" '((0 . "INSERT"))) i 0)
(while (< i (sslength ss))
  (setq e (ssname ss i) p (cdr (assoc 10 (entget e))))
  (if (and (equal (car p) 2527.543 0.01) (equal (cadr p) 1573.4896 0.01)) (setq rail e))
  (setq i (1+ i)))
(if (null rail) (princ "\nRAIL-NOT-FOUND\n"))
(command "_.COPY" rail "" (list 2527.54323342981 1573.489645820266) (list 3423.34323342981 1573.489645820266))
(cell 3401.0 1508.2 3667.0 1664.0)
(cap "letour-ly-k2810412j" 3534.0 1640.8)
(command "_.-INSERT" (strcat "LTTMP=" dir "Letour_LY-K2810412J.dwg") (list 3426.0 1573.489645818215) 1 1 0)
(setq mark (entlast))
(command "_.EXPLODE" mark)
(command "_.-PURGE" "_B" "LTTMP" "_N")
(command "_.AUDIT" "_Y")
(command "_.ZOOM" "_E")
(princ "\nADD-LETOUR-DONE\n")
(princ)
