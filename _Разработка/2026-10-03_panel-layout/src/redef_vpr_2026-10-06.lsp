(setvar "CMDECHO" 0)
(setvar "OSMODE" 0)
(setvar "ATTREQ" 0)
(setq k 0)
(command "_.-INSERT" "D-VPR-1.5=C:/Users/marat/AppData/Local/Temp/claude/C--Users-marat-Desktop-SX------------/9b70fd8b-8c16-431e-8972-6668244a1be4/scratchpad/wb/D-VPR-1.5.dwg" (list -5000.0 -5000.0) 1 1 0)
(if (= (cdr (assoc 2 (entget (entlast)))) "D-VPR-1.5") (progn (entdel (entlast)) (setq k (1+ k))))
(command "_.-INSERT" "D-VPR-1.5-QUATTRO=C:/Users/marat/AppData/Local/Temp/claude/C--Users-marat-Desktop-SX------------/9b70fd8b-8c16-431e-8972-6668244a1be4/scratchpad/wb/D-VPR-1.5-QUATTRO.dwg" (list -5000.0 -5000.0) 1 1 0)
(if (= (cdr (assoc 2 (entget (entlast)))) "D-VPR-1.5-QUATTRO") (progn (entdel (entlast)) (setq k (1+ k))))
(command "_.-INSERT" "D-VPR-1.5-TWIN=C:/Users/marat/AppData/Local/Temp/claude/C--Users-marat-Desktop-SX------------/9b70fd8b-8c16-431e-8972-6668244a1be4/scratchpad/wb/D-VPR-1.5-TWIN.dwg" (list -5000.0 -5000.0) 1 1 0)
(if (= (cdr (assoc 2 (entget (entlast)))) "D-VPR-1.5-TWIN") (progn (entdel (entlast)) (setq k (1+ k))))
(command "_.-INSERT" "D-VPR-10=C:/Users/marat/AppData/Local/Temp/claude/C--Users-marat-Desktop-SX------------/9b70fd8b-8c16-431e-8972-6668244a1be4/scratchpad/wb/D-VPR-10.dwg" (list -5000.0 -5000.0) 1 1 0)
(if (= (cdr (assoc 2 (entget (entlast)))) "D-VPR-10") (progn (entdel (entlast)) (setq k (1+ k))))
(command "_.-INSERT" "D-VPR-10-TWIN=C:/Users/marat/AppData/Local/Temp/claude/C--Users-marat-Desktop-SX------------/9b70fd8b-8c16-431e-8972-6668244a1be4/scratchpad/wb/D-VPR-10-TWIN.dwg" (list -5000.0 -5000.0) 1 1 0)
(if (= (cdr (assoc 2 (entget (entlast)))) "D-VPR-10-TWIN") (progn (entdel (entlast)) (setq k (1+ k))))
(command "_.-INSERT" "D-VPR-16=C:/Users/marat/AppData/Local/Temp/claude/C--Users-marat-Desktop-SX------------/9b70fd8b-8c16-431e-8972-6668244a1be4/scratchpad/wb/D-VPR-16.dwg" (list -5000.0 -5000.0) 1 1 0)
(if (= (cdr (assoc 2 (entget (entlast)))) "D-VPR-16") (progn (entdel (entlast)) (setq k (1+ k))))
(command "_.-INSERT" "D-VPR-16-TWIN=C:/Users/marat/AppData/Local/Temp/claude/C--Users-marat-Desktop-SX------------/9b70fd8b-8c16-431e-8972-6668244a1be4/scratchpad/wb/D-VPR-16-TWIN.dwg" (list -5000.0 -5000.0) 1 1 0)
(if (= (cdr (assoc 2 (entget (entlast)))) "D-VPR-16-TWIN") (progn (entdel (entlast)) (setq k (1+ k))))
(command "_.-INSERT" "D-VPR-2.5=C:/Users/marat/AppData/Local/Temp/claude/C--Users-marat-Desktop-SX------------/9b70fd8b-8c16-431e-8972-6668244a1be4/scratchpad/wb/D-VPR-2.5.dwg" (list -5000.0 -5000.0) 1 1 0)
(if (= (cdr (assoc 2 (entget (entlast)))) "D-VPR-2.5") (progn (entdel (entlast)) (setq k (1+ k))))
(command "_.-INSERT" "D-VPR-2.5-3L=C:/Users/marat/AppData/Local/Temp/claude/C--Users-marat-Desktop-SX------------/9b70fd8b-8c16-431e-8972-6668244a1be4/scratchpad/wb/D-VPR-2.5-3L.dwg" (list -5000.0 -5000.0) 1 1 0)
(if (= (cdr (assoc 2 (entget (entlast)))) "D-VPR-2.5-3L") (progn (entdel (entlast)) (setq k (1+ k))))
(command "_.-INSERT" "D-VPR-2.5-QUATTRO=C:/Users/marat/AppData/Local/Temp/claude/C--Users-marat-Desktop-SX------------/9b70fd8b-8c16-431e-8972-6668244a1be4/scratchpad/wb/D-VPR-2.5-QUATTRO.dwg" (list -5000.0 -5000.0) 1 1 0)
(if (= (cdr (assoc 2 (entget (entlast)))) "D-VPR-2.5-QUATTRO") (progn (entdel (entlast)) (setq k (1+ k))))
(command "_.-INSERT" "D-VPR-2.5-TWIN=C:/Users/marat/AppData/Local/Temp/claude/C--Users-marat-Desktop-SX------------/9b70fd8b-8c16-431e-8972-6668244a1be4/scratchpad/wb/D-VPR-2.5-TWIN.dwg" (list -5000.0 -5000.0) 1 1 0)
(if (= (cdr (assoc 2 (entget (entlast)))) "D-VPR-2.5-TWIN") (progn (entdel (entlast)) (setq k (1+ k))))
(command "_.-INSERT" "D-VPR-4=C:/Users/marat/AppData/Local/Temp/claude/C--Users-marat-Desktop-SX------------/9b70fd8b-8c16-431e-8972-6668244a1be4/scratchpad/wb/D-VPR-4.dwg" (list -5000.0 -5000.0) 1 1 0)
(if (= (cdr (assoc 2 (entget (entlast)))) "D-VPR-4") (progn (entdel (entlast)) (setq k (1+ k))))
(command "_.-INSERT" "D-VPR-4-QUATTRO=C:/Users/marat/AppData/Local/Temp/claude/C--Users-marat-Desktop-SX------------/9b70fd8b-8c16-431e-8972-6668244a1be4/scratchpad/wb/D-VPR-4-QUATTRO.dwg" (list -5000.0 -5000.0) 1 1 0)
(if (= (cdr (assoc 2 (entget (entlast)))) "D-VPR-4-QUATTRO") (progn (entdel (entlast)) (setq k (1+ k))))
(command "_.-INSERT" "D-VPR-4-TWIN=C:/Users/marat/AppData/Local/Temp/claude/C--Users-marat-Desktop-SX------------/9b70fd8b-8c16-431e-8972-6668244a1be4/scratchpad/wb/D-VPR-4-TWIN.dwg" (list -5000.0 -5000.0) 1 1 0)
(if (= (cdr (assoc 2 (entget (entlast)))) "D-VPR-4-TWIN") (progn (entdel (entlast)) (setq k (1+ k))))
(command "_.-INSERT" "D-VPR-6=C:/Users/marat/AppData/Local/Temp/claude/C--Users-marat-Desktop-SX------------/9b70fd8b-8c16-431e-8972-6668244a1be4/scratchpad/wb/D-VPR-6.dwg" (list -5000.0 -5000.0) 1 1 0)
(if (= (cdr (assoc 2 (entget (entlast)))) "D-VPR-6") (progn (entdel (entlast)) (setq k (1+ k))))
(command "_.-INSERT" "D-VPR-6-TWIN=C:/Users/marat/AppData/Local/Temp/claude/C--Users-marat-Desktop-SX------------/9b70fd8b-8c16-431e-8972-6668244a1be4/scratchpad/wb/D-VPR-6-TWIN.dwg" (list -5000.0 -5000.0) 1 1 0)
(if (= (cdr (assoc 2 (entget (entlast)))) "D-VPR-6-TWIN") (progn (entdel (entlast)) (setq k (1+ k))))
(command "_.-INSERT" "VPR-1.5-BU=C:/Users/marat/AppData/Local/Temp/claude/C--Users-marat-Desktop-SX------------/9b70fd8b-8c16-431e-8972-6668244a1be4/scratchpad/wb/VPR-1.5-BU.dwg" (list -5000.0 -5000.0) 1 1 0)
(if (= (cdr (assoc 2 (entget (entlast)))) "VPR-1.5-BU") (progn (entdel (entlast)) (setq k (1+ k))))
(command "_.-INSERT" "VPR-1.5-GY=C:/Users/marat/AppData/Local/Temp/claude/C--Users-marat-Desktop-SX------------/9b70fd8b-8c16-431e-8972-6668244a1be4/scratchpad/wb/VPR-1.5-GY.dwg" (list -5000.0 -5000.0) 1 1 0)
(if (= (cdr (assoc 2 (entget (entlast)))) "VPR-1.5-GY") (progn (entdel (entlast)) (setq k (1+ k))))
(command "_.-INSERT" "VPR-1.5-OR=C:/Users/marat/AppData/Local/Temp/claude/C--Users-marat-Desktop-SX------------/9b70fd8b-8c16-431e-8972-6668244a1be4/scratchpad/wb/VPR-1.5-OR.dwg" (list -5000.0 -5000.0) 1 1 0)
(if (= (cdr (assoc 2 (entget (entlast)))) "VPR-1.5-OR") (progn (entdel (entlast)) (setq k (1+ k))))
(command "_.-INSERT" "VPR-1.5-PE=C:/Users/marat/AppData/Local/Temp/claude/C--Users-marat-Desktop-SX------------/9b70fd8b-8c16-431e-8972-6668244a1be4/scratchpad/wb/VPR-1.5-PE.dwg" (list -5000.0 -5000.0) 1 1 0)
(if (= (cdr (assoc 2 (entget (entlast)))) "VPR-1.5-PE") (progn (entdel (entlast)) (setq k (1+ k))))
(command "_.-INSERT" "VPR-1.5-QUATTRO-GY=C:/Users/marat/AppData/Local/Temp/claude/C--Users-marat-Desktop-SX------------/9b70fd8b-8c16-431e-8972-6668244a1be4/scratchpad/wb/VPR-1.5-QUATTRO-GY.dwg" (list -5000.0 -5000.0) 1 1 0)
(if (= (cdr (assoc 2 (entget (entlast)))) "VPR-1.5-QUATTRO-GY") (progn (entdel (entlast)) (setq k (1+ k))))
(command "_.-INSERT" "VPR-1.5-QUATTRO-OR=C:/Users/marat/AppData/Local/Temp/claude/C--Users-marat-Desktop-SX------------/9b70fd8b-8c16-431e-8972-6668244a1be4/scratchpad/wb/VPR-1.5-QUATTRO-OR.dwg" (list -5000.0 -5000.0) 1 1 0)
(if (= (cdr (assoc 2 (entget (entlast)))) "VPR-1.5-QUATTRO-OR") (progn (entdel (entlast)) (setq k (1+ k))))
(command "_.-INSERT" "VPR-1.5-QUATTRO-PE=C:/Users/marat/AppData/Local/Temp/claude/C--Users-marat-Desktop-SX------------/9b70fd8b-8c16-431e-8972-6668244a1be4/scratchpad/wb/VPR-1.5-QUATTRO-PE.dwg" (list -5000.0 -5000.0) 1 1 0)
(if (= (cdr (assoc 2 (entget (entlast)))) "VPR-1.5-QUATTRO-PE") (progn (entdel (entlast)) (setq k (1+ k))))
(command "_.-INSERT" "VPR-1.5-TWIN-BU=C:/Users/marat/AppData/Local/Temp/claude/C--Users-marat-Desktop-SX------------/9b70fd8b-8c16-431e-8972-6668244a1be4/scratchpad/wb/VPR-1.5-TWIN-BU.dwg" (list -5000.0 -5000.0) 1 1 0)
(if (= (cdr (assoc 2 (entget (entlast)))) "VPR-1.5-TWIN-BU") (progn (entdel (entlast)) (setq k (1+ k))))
(command "_.-INSERT" "VPR-1.5-TWIN-GY=C:/Users/marat/AppData/Local/Temp/claude/C--Users-marat-Desktop-SX------------/9b70fd8b-8c16-431e-8972-6668244a1be4/scratchpad/wb/VPR-1.5-TWIN-GY.dwg" (list -5000.0 -5000.0) 1 1 0)
(if (= (cdr (assoc 2 (entget (entlast)))) "VPR-1.5-TWIN-GY") (progn (entdel (entlast)) (setq k (1+ k))))
(command "_.-INSERT" "VPR-1.5-TWIN-OR=C:/Users/marat/AppData/Local/Temp/claude/C--Users-marat-Desktop-SX------------/9b70fd8b-8c16-431e-8972-6668244a1be4/scratchpad/wb/VPR-1.5-TWIN-OR.dwg" (list -5000.0 -5000.0) 1 1 0)
(if (= (cdr (assoc 2 (entget (entlast)))) "VPR-1.5-TWIN-OR") (progn (entdel (entlast)) (setq k (1+ k))))
(command "_.-INSERT" "VPR-1.5-TWIN-PE=C:/Users/marat/AppData/Local/Temp/claude/C--Users-marat-Desktop-SX------------/9b70fd8b-8c16-431e-8972-6668244a1be4/scratchpad/wb/VPR-1.5-TWIN-PE.dwg" (list -5000.0 -5000.0) 1 1 0)
(if (= (cdr (assoc 2 (entget (entlast)))) "VPR-1.5-TWIN-PE") (progn (entdel (entlast)) (setq k (1+ k))))
(command "_.-INSERT" "VPR-10-BU=C:/Users/marat/AppData/Local/Temp/claude/C--Users-marat-Desktop-SX------------/9b70fd8b-8c16-431e-8972-6668244a1be4/scratchpad/wb/VPR-10-BU.dwg" (list -5000.0 -5000.0) 1 1 0)
(if (= (cdr (assoc 2 (entget (entlast)))) "VPR-10-BU") (progn (entdel (entlast)) (setq k (1+ k))))
(command "_.-INSERT" "VPR-10-GY=C:/Users/marat/AppData/Local/Temp/claude/C--Users-marat-Desktop-SX------------/9b70fd8b-8c16-431e-8972-6668244a1be4/scratchpad/wb/VPR-10-GY.dwg" (list -5000.0 -5000.0) 1 1 0)
(if (= (cdr (assoc 2 (entget (entlast)))) "VPR-10-GY") (progn (entdel (entlast)) (setq k (1+ k))))
(command "_.-INSERT" "VPR-10-PE-YG=C:/Users/marat/AppData/Local/Temp/claude/C--Users-marat-Desktop-SX------------/9b70fd8b-8c16-431e-8972-6668244a1be4/scratchpad/wb/VPR-10-PE-YG.dwg" (list -5000.0 -5000.0) 1 1 0)
(if (= (cdr (assoc 2 (entget (entlast)))) "VPR-10-PE-YG") (progn (entdel (entlast)) (setq k (1+ k))))
(command "_.-INSERT" "VPR-10-TWIN-GY=C:/Users/marat/AppData/Local/Temp/claude/C--Users-marat-Desktop-SX------------/9b70fd8b-8c16-431e-8972-6668244a1be4/scratchpad/wb/VPR-10-TWIN-GY.dwg" (list -5000.0 -5000.0) 1 1 0)
(if (= (cdr (assoc 2 (entget (entlast)))) "VPR-10-TWIN-GY") (progn (entdel (entlast)) (setq k (1+ k))))
(command "_.-INSERT" "VPR-16-BU=C:/Users/marat/AppData/Local/Temp/claude/C--Users-marat-Desktop-SX------------/9b70fd8b-8c16-431e-8972-6668244a1be4/scratchpad/wb/VPR-16-BU.dwg" (list -5000.0 -5000.0) 1 1 0)
(if (= (cdr (assoc 2 (entget (entlast)))) "VPR-16-BU") (progn (entdel (entlast)) (setq k (1+ k))))
(command "_.-INSERT" "VPR-16-GY=C:/Users/marat/AppData/Local/Temp/claude/C--Users-marat-Desktop-SX------------/9b70fd8b-8c16-431e-8972-6668244a1be4/scratchpad/wb/VPR-16-GY.dwg" (list -5000.0 -5000.0) 1 1 0)
(if (= (cdr (assoc 2 (entget (entlast)))) "VPR-16-GY") (progn (entdel (entlast)) (setq k (1+ k))))
(command "_.-INSERT" "VPR-16-PE-YG=C:/Users/marat/AppData/Local/Temp/claude/C--Users-marat-Desktop-SX------------/9b70fd8b-8c16-431e-8972-6668244a1be4/scratchpad/wb/VPR-16-PE-YG.dwg" (list -5000.0 -5000.0) 1 1 0)
(if (= (cdr (assoc 2 (entget (entlast)))) "VPR-16-PE-YG") (progn (entdel (entlast)) (setq k (1+ k))))
(command "_.-INSERT" "VPR-16-TWIN-GY=C:/Users/marat/AppData/Local/Temp/claude/C--Users-marat-Desktop-SX------------/9b70fd8b-8c16-431e-8972-6668244a1be4/scratchpad/wb/VPR-16-TWIN-GY.dwg" (list -5000.0 -5000.0) 1 1 0)
(if (= (cdr (assoc 2 (entget (entlast)))) "VPR-16-TWIN-GY") (progn (entdel (entlast)) (setq k (1+ k))))
(command "_.-INSERT" "VPR-2.5-3L-BU=C:/Users/marat/AppData/Local/Temp/claude/C--Users-marat-Desktop-SX------------/9b70fd8b-8c16-431e-8972-6668244a1be4/scratchpad/wb/VPR-2.5-3L-BU.dwg" (list -5000.0 -5000.0) 1 1 0)
(if (= (cdr (assoc 2 (entget (entlast)))) "VPR-2.5-3L-BU") (progn (entdel (entlast)) (setq k (1+ k))))
(command "_.-INSERT" "VPR-2.5-3L-GY=C:/Users/marat/AppData/Local/Temp/claude/C--Users-marat-Desktop-SX------------/9b70fd8b-8c16-431e-8972-6668244a1be4/scratchpad/wb/VPR-2.5-3L-GY.dwg" (list -5000.0 -5000.0) 1 1 0)
(if (= (cdr (assoc 2 (entget (entlast)))) "VPR-2.5-3L-GY") (progn (entdel (entlast)) (setq k (1+ k))))
(command "_.-INSERT" "VPR-2.5-3L-PE-YG=C:/Users/marat/AppData/Local/Temp/claude/C--Users-marat-Desktop-SX------------/9b70fd8b-8c16-431e-8972-6668244a1be4/scratchpad/wb/VPR-2.5-3L-PE-YG.dwg" (list -5000.0 -5000.0) 1 1 0)
(if (= (cdr (assoc 2 (entget (entlast)))) "VPR-2.5-3L-PE-YG") (progn (entdel (entlast)) (setq k (1+ k))))
(command "_.-INSERT" "VPR-2.5-3L-PV-BU=C:/Users/marat/AppData/Local/Temp/claude/C--Users-marat-Desktop-SX------------/9b70fd8b-8c16-431e-8972-6668244a1be4/scratchpad/wb/VPR-2.5-3L-PV-BU.dwg" (list -5000.0 -5000.0) 1 1 0)
(if (= (cdr (assoc 2 (entget (entlast)))) "VPR-2.5-3L-PV-BU") (progn (entdel (entlast)) (setq k (1+ k))))
(command "_.-INSERT" "VPR-2.5-3L-PV-GY=C:/Users/marat/AppData/Local/Temp/claude/C--Users-marat-Desktop-SX------------/9b70fd8b-8c16-431e-8972-6668244a1be4/scratchpad/wb/VPR-2.5-3L-PV-GY.dwg" (list -5000.0 -5000.0) 1 1 0)
(if (= (cdr (assoc 2 (entget (entlast)))) "VPR-2.5-3L-PV-GY") (progn (entdel (entlast)) (setq k (1+ k))))
(command "_.-INSERT" "VPR-2.5-BU=C:/Users/marat/AppData/Local/Temp/claude/C--Users-marat-Desktop-SX------------/9b70fd8b-8c16-431e-8972-6668244a1be4/scratchpad/wb/VPR-2.5-BU.dwg" (list -5000.0 -5000.0) 1 1 0)
(if (= (cdr (assoc 2 (entget (entlast)))) "VPR-2.5-BU") (progn (entdel (entlast)) (setq k (1+ k))))
(command "_.-INSERT" "VPR-2.5-GY=C:/Users/marat/AppData/Local/Temp/claude/C--Users-marat-Desktop-SX------------/9b70fd8b-8c16-431e-8972-6668244a1be4/scratchpad/wb/VPR-2.5-GY.dwg" (list -5000.0 -5000.0) 1 1 0)
(if (= (cdr (assoc 2 (entget (entlast)))) "VPR-2.5-GY") (progn (entdel (entlast)) (setq k (1+ k))))
(command "_.-INSERT" "VPR-2.5-PE-YG=C:/Users/marat/AppData/Local/Temp/claude/C--Users-marat-Desktop-SX------------/9b70fd8b-8c16-431e-8972-6668244a1be4/scratchpad/wb/VPR-2.5-PE-YG.dwg" (list -5000.0 -5000.0) 1 1 0)
(if (= (cdr (assoc 2 (entget (entlast)))) "VPR-2.5-PE-YG") (progn (entdel (entlast)) (setq k (1+ k))))
(command "_.-INSERT" "VPR-2.5-QUATTRO-BU=C:/Users/marat/AppData/Local/Temp/claude/C--Users-marat-Desktop-SX------------/9b70fd8b-8c16-431e-8972-6668244a1be4/scratchpad/wb/VPR-2.5-QUATTRO-BU.dwg" (list -5000.0 -5000.0) 1 1 0)
(if (= (cdr (assoc 2 (entget (entlast)))) "VPR-2.5-QUATTRO-BU") (progn (entdel (entlast)) (setq k (1+ k))))
(command "_.-INSERT" "VPR-2.5-QUATTRO-GY=C:/Users/marat/AppData/Local/Temp/claude/C--Users-marat-Desktop-SX------------/9b70fd8b-8c16-431e-8972-6668244a1be4/scratchpad/wb/VPR-2.5-QUATTRO-GY.dwg" (list -5000.0 -5000.0) 1 1 0)
(if (= (cdr (assoc 2 (entget (entlast)))) "VPR-2.5-QUATTRO-GY") (progn (entdel (entlast)) (setq k (1+ k))))
(command "_.-INSERT" "VPR-2.5-QUATTRO-PE=C:/Users/marat/AppData/Local/Temp/claude/C--Users-marat-Desktop-SX------------/9b70fd8b-8c16-431e-8972-6668244a1be4/scratchpad/wb/VPR-2.5-QUATTRO-PE.dwg" (list -5000.0 -5000.0) 1 1 0)
(if (= (cdr (assoc 2 (entget (entlast)))) "VPR-2.5-QUATTRO-PE") (progn (entdel (entlast)) (setq k (1+ k))))
(command "_.-INSERT" "VPR-2.5-TWIN-BU=C:/Users/marat/AppData/Local/Temp/claude/C--Users-marat-Desktop-SX------------/9b70fd8b-8c16-431e-8972-6668244a1be4/scratchpad/wb/VPR-2.5-TWIN-BU.dwg" (list -5000.0 -5000.0) 1 1 0)
(if (= (cdr (assoc 2 (entget (entlast)))) "VPR-2.5-TWIN-BU") (progn (entdel (entlast)) (setq k (1+ k))))
(command "_.-INSERT" "VPR-2.5-TWIN-GY=C:/Users/marat/AppData/Local/Temp/claude/C--Users-marat-Desktop-SX------------/9b70fd8b-8c16-431e-8972-6668244a1be4/scratchpad/wb/VPR-2.5-TWIN-GY.dwg" (list -5000.0 -5000.0) 1 1 0)
(if (= (cdr (assoc 2 (entget (entlast)))) "VPR-2.5-TWIN-GY") (progn (entdel (entlast)) (setq k (1+ k))))
(command "_.-INSERT" "VPR-2.5-TWIN-PE-YG=C:/Users/marat/AppData/Local/Temp/claude/C--Users-marat-Desktop-SX------------/9b70fd8b-8c16-431e-8972-6668244a1be4/scratchpad/wb/VPR-2.5-TWIN-PE-YG.dwg" (list -5000.0 -5000.0) 1 1 0)
(if (= (cdr (assoc 2 (entget (entlast)))) "VPR-2.5-TWIN-PE-YG") (progn (entdel (entlast)) (setq k (1+ k))))
(command "_.-INSERT" "VPR-4-BU=C:/Users/marat/AppData/Local/Temp/claude/C--Users-marat-Desktop-SX------------/9b70fd8b-8c16-431e-8972-6668244a1be4/scratchpad/wb/VPR-4-BU.dwg" (list -5000.0 -5000.0) 1 1 0)
(if (= (cdr (assoc 2 (entget (entlast)))) "VPR-4-BU") (progn (entdel (entlast)) (setq k (1+ k))))
(command "_.-INSERT" "VPR-4-GY=C:/Users/marat/AppData/Local/Temp/claude/C--Users-marat-Desktop-SX------------/9b70fd8b-8c16-431e-8972-6668244a1be4/scratchpad/wb/VPR-4-GY.dwg" (list -5000.0 -5000.0) 1 1 0)
(if (= (cdr (assoc 2 (entget (entlast)))) "VPR-4-GY") (progn (entdel (entlast)) (setq k (1+ k))))
(command "_.-INSERT" "VPR-4-PE-YG=C:/Users/marat/AppData/Local/Temp/claude/C--Users-marat-Desktop-SX------------/9b70fd8b-8c16-431e-8972-6668244a1be4/scratchpad/wb/VPR-4-PE-YG.dwg" (list -5000.0 -5000.0) 1 1 0)
(if (= (cdr (assoc 2 (entget (entlast)))) "VPR-4-PE-YG") (progn (entdel (entlast)) (setq k (1+ k))))
(command "_.-INSERT" "VPR-4-QUATTRO-BU=C:/Users/marat/AppData/Local/Temp/claude/C--Users-marat-Desktop-SX------------/9b70fd8b-8c16-431e-8972-6668244a1be4/scratchpad/wb/VPR-4-QUATTRO-BU.dwg" (list -5000.0 -5000.0) 1 1 0)
(if (= (cdr (assoc 2 (entget (entlast)))) "VPR-4-QUATTRO-BU") (progn (entdel (entlast)) (setq k (1+ k))))
(command "_.-INSERT" "VPR-4-QUATTRO-GY=C:/Users/marat/AppData/Local/Temp/claude/C--Users-marat-Desktop-SX------------/9b70fd8b-8c16-431e-8972-6668244a1be4/scratchpad/wb/VPR-4-QUATTRO-GY.dwg" (list -5000.0 -5000.0) 1 1 0)
(if (= (cdr (assoc 2 (entget (entlast)))) "VPR-4-QUATTRO-GY") (progn (entdel (entlast)) (setq k (1+ k))))
(command "_.-INSERT" "VPR-4-QUATTRO-PE=C:/Users/marat/AppData/Local/Temp/claude/C--Users-marat-Desktop-SX------------/9b70fd8b-8c16-431e-8972-6668244a1be4/scratchpad/wb/VPR-4-QUATTRO-PE.dwg" (list -5000.0 -5000.0) 1 1 0)
(if (= (cdr (assoc 2 (entget (entlast)))) "VPR-4-QUATTRO-PE") (progn (entdel (entlast)) (setq k (1+ k))))
(command "_.-INSERT" "VPR-4-TWIN-BU=C:/Users/marat/AppData/Local/Temp/claude/C--Users-marat-Desktop-SX------------/9b70fd8b-8c16-431e-8972-6668244a1be4/scratchpad/wb/VPR-4-TWIN-BU.dwg" (list -5000.0 -5000.0) 1 1 0)
(if (= (cdr (assoc 2 (entget (entlast)))) "VPR-4-TWIN-BU") (progn (entdel (entlast)) (setq k (1+ k))))
(command "_.-INSERT" "VPR-4-TWIN-GY=C:/Users/marat/AppData/Local/Temp/claude/C--Users-marat-Desktop-SX------------/9b70fd8b-8c16-431e-8972-6668244a1be4/scratchpad/wb/VPR-4-TWIN-GY.dwg" (list -5000.0 -5000.0) 1 1 0)
(if (= (cdr (assoc 2 (entget (entlast)))) "VPR-4-TWIN-GY") (progn (entdel (entlast)) (setq k (1+ k))))
(command "_.-INSERT" "VPR-4-TWIN-PE-YG=C:/Users/marat/AppData/Local/Temp/claude/C--Users-marat-Desktop-SX------------/9b70fd8b-8c16-431e-8972-6668244a1be4/scratchpad/wb/VPR-4-TWIN-PE-YG.dwg" (list -5000.0 -5000.0) 1 1 0)
(if (= (cdr (assoc 2 (entget (entlast)))) "VPR-4-TWIN-PE-YG") (progn (entdel (entlast)) (setq k (1+ k))))
(command "_.-INSERT" "VPR-6-BU=C:/Users/marat/AppData/Local/Temp/claude/C--Users-marat-Desktop-SX------------/9b70fd8b-8c16-431e-8972-6668244a1be4/scratchpad/wb/VPR-6-BU.dwg" (list -5000.0 -5000.0) 1 1 0)
(if (= (cdr (assoc 2 (entget (entlast)))) "VPR-6-BU") (progn (entdel (entlast)) (setq k (1+ k))))
(command "_.-INSERT" "VPR-6-GY=C:/Users/marat/AppData/Local/Temp/claude/C--Users-marat-Desktop-SX------------/9b70fd8b-8c16-431e-8972-6668244a1be4/scratchpad/wb/VPR-6-GY.dwg" (list -5000.0 -5000.0) 1 1 0)
(if (= (cdr (assoc 2 (entget (entlast)))) "VPR-6-GY") (progn (entdel (entlast)) (setq k (1+ k))))
(command "_.-INSERT" "VPR-6-PE-YG=C:/Users/marat/AppData/Local/Temp/claude/C--Users-marat-Desktop-SX------------/9b70fd8b-8c16-431e-8972-6668244a1be4/scratchpad/wb/VPR-6-PE-YG.dwg" (list -5000.0 -5000.0) 1 1 0)
(if (= (cdr (assoc 2 (entget (entlast)))) "VPR-6-PE-YG") (progn (entdel (entlast)) (setq k (1+ k))))
(command "_.-INSERT" "VPR-6-TWIN-GY=C:/Users/marat/AppData/Local/Temp/claude/C--Users-marat-Desktop-SX------------/9b70fd8b-8c16-431e-8972-6668244a1be4/scratchpad/wb/VPR-6-TWIN-GY.dwg" (list -5000.0 -5000.0) 1 1 0)
(if (= (cdr (assoc 2 (entget (entlast)))) "VPR-6-TWIN-GY") (progn (entdel (entlast)) (setq k (1+ k))))
(command "_.AUDIT" "_Y")
(princ (strcat "
REDEF-VPR " (itoa k) "
"))
(princ)
