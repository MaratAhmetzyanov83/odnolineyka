(setq zzchecks nil)
(defun zzcheck (name ok) (setq zzchecks (cons (list name (if ok "PASS" "FAIL")) zzchecks)))
(setq zzvals '((nil nil nil nil nil nil nil nil nil nil nil nil nil nil nil nil) (nil nil nil nil nil nil nil nil nil nil nil nil nil nil nil nil) (nil nil nil nil nil nil nil nil nil nil nil nil nil nil nil nil) ("ЩР-1" nil nil nil nil nil nil nil nil nil "КРМ" nil nil "РАСЧЁТ Рр (СП 256)" "Весь щит (аварийн.)" "Секция 1") ("P" "кВт" nil "Руст=" 5.7299999999999995 "кВт" "L1р=" 1.3662 "кВт" nil "Не требуется 
СП256 П.7.3.2" "кВАр" nil "Руст (без «Нет»), кВт" 5.7299999999999995 5.7299999999999995) (nil nil nil "Рр=" 3.9537 "кВт" "L2р=" 1.2558000000000002 "кВт" nil nil nil nil "Руст быт, кВт" 0.0 0.0) ("P(L)" "кВт" nil "Iр=" 6.227178456054211 "А" "L3р=" 1.3317000000000003 "кВт" nil nil nil nil "Кс быт (табл. СП 256)" 0.8 0.8) ("P(L)" "%" nil "Cos(ф)=" 0.95 nil nil nil nil nil nil nil nil "Рр сил = Σ P·Кс, кВт" 3.9537 3.9537) ("ΔP(L)" "%" nil "Кс=" 0.6900000000000001 nil nil nil nil nil nil nil nil "Рр пост (Кс = 1), кВт" 0.0 0.0) ("Iпуск (1ф)" "А" nil nil nil nil nil nil nil nil nil nil nil "Рр = быт·Кс + Ко·сил + пост, кВт" 3.9537 3.9537) ("Iпуск (3ф)" "А" nil nil nil nil nil nil nil nil nil nil nil "Кс итоговый = Рр / Руст" 0.6900000000000001 0.6900000000000001) (nil nil nil nil nil nil nil nil nil nil nil nil nil "Iр по наиб. нагруж. фазе, А" 6.227178456054211 6.227178456054211) ("empty-panel" nil nil nil nil nil nil nil nil nil "КРМ" nil nil "РАСЧЁТ Рр (СП 256)" "Весь щит (аварийн.)" "Секция 1") ("P" "кВт" nil "Руст=" nil "кВт" "L1р=" nil "кВт" nil -2146826273 "кВАр" nil "Руст (без «Нет»), кВт" nil nil) (nil nil nil "Рр=" nil "кВт" "L2р=" nil "кВт" nil nil nil nil "Руст быт, кВт" nil nil) ("P(L)" "кВт" nil "Iр=" nil "А" "L3р=" nil "кВт" nil nil nil nil "Кс быт (табл. СП 256)" nil nil) ("P(L)" "%" nil "Cos(ф)=" 0.95 nil nil nil nil nil nil nil nil "Рр сил = Σ P·Кс, кВт" nil nil) ("ΔP(L)" "%" nil "Кс=" nil nil nil nil nil nil nil nil nil "Рр пост (Кс = 1), кВт" nil nil) ("Iпуск" "А" nil nil nil nil nil nil nil nil nil nil nil "Рр = быт·Кс + Ко·сил + пост, кВт" nil nil) ("Iпуск (3ф)" "А" nil nil nil nil nil nil nil nil nil nil nil "Кс итоговый = Рр / Руст" nil nil) (nil nil nil nil nil nil nil nil nil nil nil nil nil "Iр по наиб. нагруж. фазе, А" nil nil) (-2146826246 nil nil nil nil nil nil nil nil nil "КРМ" nil nil "РАСЧЁТ Рр (СП 256)" "Весь щит (аварийн.)" "Секция 1") ("P" "кВт" nil "Руст=" nil "кВт" "L1р=" -2146826273 "кВт" nil -2146826273 "кВАр" nil "Руст (без «Нет»), кВт" nil nil) (nil nil nil "Рр=" nil "кВт" "L2р=" -2146826273 "кВт" nil nil nil nil "Руст быт, кВт" nil nil) ("P(L)" "кВт" nil "Iр=" nil "А" "L3р=" -2146826273 "кВт" nil nil nil nil "Кс быт (табл. СП 256)" nil nil) ("P(L)" "%" nil "Cos(ф)=" 0.95 nil nil nil nil nil nil nil nil "Рр сил = Σ P·Кс, кВт" nil nil) ("ΔP(L)" "%" nil "Кс=" nil nil nil nil nil nil nil nil nil "Рр пост (Кс = 1), кВт" nil nil) ("Iпуск" "А" nil nil nil nil nil nil nil nil nil nil nil "Рр = быт·Кс + Ко·сил + пост, кВт" nil nil) ("Iпуск (3ф)" "А" nil nil nil nil nil nil nil nil nil nil nil "Кс итоговый = Рр / Руст" nil nil) (nil nil nil nil nil nil nil nil nil nil nil nil nil "Iр по наиб. нагруж. фазе, А" nil nil) (nil nil nil nil nil nil nil nil nil nil nil nil nil nil nil nil) (nil nil nil nil nil nil nil nil nil nil nil nil nil nil nil nil)))
(zzcheck "source totals" (equal (sx:summary-values zzvals sx:tagpanel) sx:summary 0.000001))
(zzcheck "empty table with default cos" (null (sx:summary-values zzvals "empty-panel")))
(setq zzbad (subst (subst "bad-number" (nth 4 (nth 4 zzvals)) (nth 4 zzvals)) (nth 4 zzvals) zzvals))
(zzcheck "invalid filled table skipped" (null (sx:summary-values zzbad sx:tagpanel)))
(zzcheck "two decimals with DIMZIN=8" (progn (setq zzz (getvar "DIMZIN")) (setvar "DIMZIN" 8) (setq zzt (sx:summary-num 0.2)) (setvar "DIMZIN" zzz) (= zzt "0,20")))
(setq zzsum 0 zzout 0 zzwhite 0 zzsumob nil)
(vlax-for ob sx:ms
  (setq e (vlax-vla-object->ename ob) xd (sx:xd-get e))
  (if (equal xd (list sx:tagpanel "U")) (setq zzsum (1+ zzsum) zzsumob ob))
  (if (and (= (vla-get-objectname ob) "AcDbBlockReference") (= (vla-get-layer ob) sx:BL)
           (= (vla-get-effectivename ob) sx:bOut))
    (progn (setq zzout (1+ zzout))
      (if (/= (cdr (assoc 420 (entget e))) sx:red-rgb) (setq zzwhite (1+ zzwhite))))))
(zzcheck "exactly one totals table" (= zzsum 1))
(zzcheck "all fallback outlets red" (and (> zzout 0) (= zzwhite 0)))
(zzcheck "table location and dimensions" (and zzsumob (equal (vla-get-width zzsumob) 120.0 0.000001) (equal (vla-get-height zzsumob) 40.0 0.000001) (equal (sx:pt 7.56437443444702 -5.3734190440593) (vlax-safearray->list (vlax-variant-value (vla-get-insertionpoint zzsumob))) 0.000001)))
(zzcheck "summary values and formatting" (and (= (vla-gettext zzsumob 0 1) "5,73") (= (vla-gettext zzsumob 1 1) "3,95") (= (vla-gettext zzsumob 2 1) "6,23") (= (vla-gettext zzsumob 0 4) "1,37") (= (vla-gettext zzsumob 1 4) "1,26") (= (vla-gettext zzsumob 2 4) "1,33") (= (vla-gettext zzsumob 3 1) "0,95") (= (vla-gettext zzsumob 4 1) "0,69")))
;; Selecting totals updates only totals; no line is expanded into selection.
(setq sx:part T zzkeys (sx:sel-units '("U") sx:preview-draw))
(zzcheck "summary-only selection" (and (equal zzkeys '("U")) (null sx:onlyP) (null sx:onlyG) (null sx:onlyS)))
(sx:summary-capture) (sx:del-keys sx:tagpanel zzkeys) (sx:draw-summary)
(setq zzsaved sx:summary sx:summary nil)
(sx:summary-capture) (sx:del-keys sx:tagpanel '("U")) (sx:draw-summary)
(setq zzsum 0)
(vlax-for ob sx:ms (if (equal (sx:xd-get (vlax-vla-object->ename ob)) (list sx:tagpanel "U")) (setq zzsum (1+ zzsum))))
(zzcheck "remove stale table when no totals" (= zzsum 0))
(setq sx:summary zzsaved) (sx:draw-summary) (setq sx:part nil)
(setq f (open "C:/Users/user/Desktop/02_Справочники_CAD_Revit/odnolineyka/_Разработка/2026-10-09_incoming/totals_verification.txt" "w")) (prin1 (reverse zzchecks) f) (close f)
(vla-regen sx:doc 1) (vla-save sx:doc) (princ)
