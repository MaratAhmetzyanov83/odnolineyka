(if (= (getvar "DWGNAME") "03_Чертежи ЭОМ_ХБК.dwg")
  (progn (setq zzn 0)
    (foreach h '("211306" "211312" "21131D" "211328" "211333" "21133E" "211349" "211354" "21135F" "21136A" "211375" "211380" "21138B" "211396" "2113A1" "2113AC" "2113B7" "2113C2" "2113CD" "2113D8" "2113E3" "2113EE" "2113F9" "211404" "21140F" "21141A" "211425" "211430" "21143B" "211446" "211451" "21145C" "211467" "211472" "21147D" "211488" "211493" "21149E" "2114A9" "2114B4" "2114BF" "2114CA" "2114D5" "2114E0" "2114EB" "2114F6" "211501" "21150C" "211517" "211522" "21152D" "211538" "211543" "21154E" "211559" "211564" "21156F" "21157A" "211585" "211590" "21159B" "2115A6" "2115B1" "2115BC" "2115C7" "2115D2" "2115DD" "2115E8" "2115F3" "2115FE" "211609" "211614" "21161F" "21162A" "211635" "211640" "21164B" "211656" "211661" "21166C" "211677" "211682" "21168D" "211698" "2116A3" "2116AE" "2116B9" "2116C4" "2116CF" "2116DA" "2116E5" "2116F0" "2116FB" "211706" "211711" "21171C" "211727" "211732" "21173D" "211748" "211753" "21175E" "211769" "211774" "21177F" "21178A" "211795" "2117A0" "2117AB" "2117B6" "2117C1" "2117CC" "2117D7" "2117E2" "2117ED" "2117F8" "211803" "21180E" "211819" "211824" "21182F" "21183A" "211845" "211850" "21185B" "211866" "211871" "21187C" "211887" "211892" "21189D" "2118A8" "2118B3" "2118BE" "2118C9" "2118D4" "2118DF" "2118EA" "2118F5" "211900" "21190B" "211916" "211921" "21192C" "211937" "211942" "21194D" "211958" "211963" "21196E" "211979" "211984" "21198F" "21199A" "2119A5" "2119B0" "2119BB" "2119C6" "2119D1" "2119DC" "2119E7" "2119F2" "2119FD" "211A08" "211A13" "211A1E" "211A29" "211A34" "211A3F" "211A4A" "211A55" "211A60" "211A6B" "211A76" "211A81" "211A8C" "211A97" "211AA2" "211AAD" "211AB8" "211AC3" "211ACE" "211AD9" "211AE4" "211AEF" "211AFA" "211B05" "211B10" "211B1B" "211B26" "211B31" "211B3C" "211B47" "211B52" "211B5D" "211B68" "211B73" "211B7E" "211B89" "211B94" "211B9F" "211BAA" "211BB5" "211BC0" "211BCB" "211BD6" "211BE1" "211BEC" "211BF7" "211C02" "211C0D" "211C18" "211C23" "211C2E" "211C39" "211C3A" "211C3B" "211C3C" "211C3D" "211C3E" "211C3F" "211C40" "211C41" "211C42" "211C43" "211C44" "211C45" "211C46" "211C47" "211C48" "211C49" "211C4A" "211C50" "211C51" "211C52" "211C53" "211C54" "211C55" "211C5B" "211C5C" "211C5D" "211C5E" "211C64" "211C65" "211C66" "211C67" "211C6D" "211C6E" "211C6F" "211C70" "211C76" "211C77" "211C78" "211C79" "211C7F" "211C80" "211C81" "211C82" "211C88" "211C89" "211C8A" "211C8B" "211C91" "211C92" "211C93" "211C94" "211C9A" "211C9B" "211C9C" "211C9D" "211CA3" "211CA4" "211CA5" "211CA6" "211CAC" "211CAD" "211CAE" "211CAF" "211CB5" "211CB6" "211CB7" "211CB8" "211CBE" "211CBF" "211CC0" "211CC1" "211CC7" "211CC8" "211CC9" "211CCA" "211CD0" "211CD1" "211CD2" "211CD3" "211CD9" "211CDA" "211CDB" "211CDC" "211CE2" "211CE3" "211CE4" "211CE5" "211CEB" "211CEC" "211CED" "211CEE" "211CF4" "211CF5" "211CF6" "211CF7" "211CFA" "211CFB" "211CFC" "211CFD" "211CFE" "211CFF" "211D00" "211D01" "211D04" "211D05" "211D06" "211D07" "211D08" "211D0D" "211D10" "211D11" "211D12" "211D13" "211D14" "211D19" "211D1C" "211D1D" "211D1E" "211D1F" "211D20" "211D25" "211D28" "211D29" "211D2A" "211D2B" "211D2C" "211D31" "211D34" "211D35" "211D36" "211D37" "211D38" "211D3D" "211D40" "211D41" "211D42" "211D43" "211D44" "211D49" "211D4C" "211D4D" "211D4E" "211D4F" "211D50" "211D55" "211D58" "211D59" "211D5A" "211D5B" "211D5C" "211D61" "211D64" "211D65" "211D66" "211D67" "211D68" "211D6D" "211D70" "211D71" "211D72" "211D73" "211D74" "211D79" "211D7C" "211D7D" "211D7E" "211D7F" "211D80" "211D85" "211D88" "211D89" "211D8A" "211D8B" "211D8C" "211D91" "211D94" "211D95" "211D96" "211D97" "211D98" "211D9D" "211DA0" "211DA1" "211DA2" "211DA3" "211DA4" "211DA9" "211DAC" "211DAD" "211DAE" "211DAF" "211DB0" "211DB5" "211DB8" "211DB9" "211DBA" "211DBB" "211DBC" "211DC1" "211DC4" "211DC5" "211DC6" "211DC7" "211DC8" "211DCD" "211DD0" "211DD1" "211DD2" "211DD3" "211DD4" "211DD9")
      (if (and (setq e (handent h)) (wcmatch (cdr (assoc 8 (entget e))) "SX_*"))
        (progn (entdel e) (setq zzn (1+ zzn)))))
    (setq f (open "C:/Users/user/Desktop/02_Справочники_CAD_Revit/odnolineyka/_Разработка/2026-10-09_incoming/cleanup_result.txt" "w")) (prin1 zzn f) (close f)
    (vla-regen (vla-get-activedocument (vlax-get-acad-object)) 1)))
(princ)
