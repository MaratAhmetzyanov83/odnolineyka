(load "C:/Users/user/Desktop/02_Справочники_CAD_Revit/odnolineyka/2_AutoCAD/Однолинейка/SX_Schema.lsp")
(setq sx:errs nil sx:part T sx:tagpanel (sx:ru '(1065 1056 45 49)))
(setq sx:verify-keys (sx:sel-units '("R|5") sx:preview-draw))
(setq sx:verify-pl sx:onlyP sx:verify-gl sx:onlyG sx:verify-sl sx:onlyS)
(setq sx:verify-lead (entmakex '((0 . "LWPOLYLINE") (100 . "AcDbEntity") (8 . "0") (100 . "AcDbPolyline") (90 . 2) (70 . 0) (10 85.0 1417.69) (10 85.0551 1505.65))))
(setq sx:verify-loop (entmakex '((0 . "LWPOLYLINE") (100 . "AcDbEntity") (8 . "0") (100 . "AcDbPolyline") (90 . 3) (70 . 0) (10 85.0 1417.69) (10 165.0 1417.69) (10 165.0 1418.99))))
(setq sx:verify-bound (entmakex '((0 . "LINE") (8 . "SX_BOUND") (10 119.073 1570.16 0.0) (11 119.073 1453.49 0.0))))
(sx:adopt-inputs sx:preview-draw)
(setq sx:verify-adopt (list (sx:xd-get sx:verify-lead) (sx:xd-get sx:verify-loop) (sx:xd-get sx:verify-bound)))
(sx:summary-capture)
(sx:del-keys sx:tagpanel sx:verify-keys)
(sx:draw-table sx:preview-recs)
(sx:draw-sheets sx:preview-draw sx:tagpanel)
(sx:draw-groups sx:preview-draw)
(sx:draw-modules sx:preview-draw)
(sx:draw-rows sx:preview-draw)
(sx:draw-summary)
(setq sx:verify-ch 0)
(vlax-for oo sx:ms
  (if (and (= (vla-get-objectname oo) "AcDbBlockReference") (= (vla-get-name oo) "SX_CH")) (setq sx:verify-ch (1+ sx:verify-ch))))
(setq sxf (open "C:/Users/user/Desktop/02_Справочники_CAD_Revit/odnolineyka/_Разработка/2026-10-09_incoming/verify_result.txt" "w"))
(prin1 (list (cons 'version sx:ver) (cons 'errors sx:errs) (cons 'places sx:verify-pl) (cons 'groups sx:verify-gl) (cons 'sheets sx:verify-sl) (cons 'adopted sx:verify-adopt) (cons 'relay-channels sx:verify-ch) (cons 'input (sx:input-p (nth 5 sx:preview-recs))) (cons 'normal (sx:input-p (nth 12 sx:preview-recs)))) sxf)
(close sxf)
(setq sx:part nil)
(vla-regen sx:doc 1)
(vla-save sx:doc)
(princ)
