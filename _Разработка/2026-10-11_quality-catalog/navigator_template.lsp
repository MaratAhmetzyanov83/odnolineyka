; Каталог компоновки. Загрузить один раз через APPLOAD, команды SXCAT / SXHOME.
(vl-load-com)
@@DATA@@
(defun sx:unique (values / result value)
  (foreach value values (if (not (member value result)) (setq result (append result (list value))))) result)
(defun sx:match (row / hay)
  (setq hay (strcase (strcat (nth 0 row) " " (nth 1 row) " " (nth 2 row) " " (nth 3 row) " " (nth 4 row) " " (nth 5 row))))
  (and (or (= sx:type "Все") (= sx:type (nth 1 row)))
       (or (= sx:maker "Все") (= sx:maker (nth 2 row)))
       (or (= sx:series "Все") (= sx:series (nth 3 row)))
       (or (= sx:query "") (vl-string-search (strcase sx:query) hay))))
(defun sx:list (key values / value)
  (start_list key) (foreach value values (add_list value)) (end_list) (set_tile key "0"))
(defun sx:detail (/ r key)
  (if (setq r (nth sx:selection sx:filtered))
    (progn
      (set_tile "title" (strcat (nth 0 r) "  " (nth 4 r)))
      (set_tile "model" (strcat (nth 2 r) "  |  " (nth 3 r)))
      (set_tile "size" (strcat (rtos (nth 9 r) 2 1) " × " (rtos (nth 10 r) 2 1) " мм  |  " (nth 11 r)))
      (set_tile "quality" (nth 12 r))
      (set_tile "definition" (nth 5 r)))
    (progn (set_tile "title" "Нет совпадений") (foreach key '("model" "size" "quality" "definition") (set_tile key "")))))
(defun sx:refresh (/ r key)
  (setq sx:filtered (vl-remove-if-not 'sx:match sx:catalog) sx:selection 0)
  (start_list "blocks")
  (foreach r sx:filtered (add_list (strcat (nth 0 r) "  |  " (nth 2 r) "  |  " (nth 4 r))))
  (end_list) (set_tile "blocks" "0")
  (set_tile "count" (strcat "Найдено: " (itoa (length sx:filtered)) " из " (itoa (length sx:catalog))))
  (foreach key '("show" "page" "select" "insert") (mode_tile key (if sx:filtered 0 1)))
  (sx:detail))
(defun sx:makers ()
  (setq sx:makers (cons "Все" (sx:unique (mapcar '(lambda (r) (nth 2 r))
    (vl-remove-if-not '(lambda (r) (or (= sx:type "Все") (= sx:type (nth 1 r)))) sx:catalog)))))
  (sx:list "maker" sx:makers) (setq sx:maker "Все") (sx:series-list))
(defun sx:series-list ()
  (setq sx:series-list (cons "Все" (sx:unique (mapcar '(lambda (r) (nth 3 r))
    (vl-remove-if-not '(lambda (r) (and (or (= sx:type "Все") (= sx:type (nth 1 r)))
      (or (= sx:maker "Все") (= sx:maker (nth 2 r))))) sx:catalog)))))
  (sx:list "series" sx:series-list) (setq sx:series "Все") (sx:refresh))
(defun sx:zoom (row / b pad)
  (setvar "TILEMODE" 1) (setq b (nth 7 row) pad (* 0.06 (max (- (nth 2 b) (nth 0 b)) (- (nth 3 b) (nth 1 b)))))
  (command "_.ZOOM" "_W" "_non" (list (- (nth 0 b) pad) (- (nth 1 b) pad)) "_non" (list (+ (nth 2 b) pad) (+ (nth 3 b) pad))))
(defun c:SXHOME () (if (tblsearch "VIEW" "00_ОГЛАВЛЕНИЕ") (command "_.-VIEW" "_R" "00_ОГЛАВЛЕНИЕ") (princ "\nОткройте DWG базы компоновки.")) (princ))
(defun c:SXGO (/ code r)
  (setq code (strcase (getstring T "\nКод блока (например S0001): ")))
  (setq r (car (vl-remove-if-not '(lambda (r) (= code (strcase (nth 0 r)))) sx:catalog)))
  (if r (sx:zoom r) (princ "\nКод не найден. Откройте поиск SXCAT.")) (princ))
(defun c:SXCAT (/ path stream dlg result row selected ss idx e point attreq oldecho b *error* line)
  (defun *error* (message)
    (if attreq (setvar "ATTREQ" attreq)) (if oldecho (setvar "CMDECHO" oldecho))
    (if (and dlg (> dlg 0)) (unload_dialog dlg)) (if path (vl-file-delete path))
    (if (not (wcmatch (strcase message) "*CANCEL*,*QUIT*,*ОТМЕН*")) (princ (strcat "\nКаталог: " message))) (princ))
  (if (not (tblsearch "VIEW" "00_ОГЛАВЛЕНИЕ"))
    (princ "\nСначала откройте DWG базы компоновки. Команды доступны в файле каталога.")
    (progn
      (setq path (vl-filename-mktemp "sxcat_" nil ".dcl") stream (open path "w" "utf8"))
      (foreach line sx:dialog-lines (write-line line stream)) (close stream)
      (setq dlg (load_dialog path))
      (if (and (> dlg 0) (new_dialog "sxcat" dlg))
        (progn
          (setq sx:type "Все" sx:maker "Все" sx:series "Все" sx:query "" sx:selection 0)
          (setq sx:types (cons "Все" (sx:unique (mapcar '(lambda (r) (nth 1 r)) sx:catalog))))
          (sx:list "type" sx:types) (sx:makers)
          (action_tile "type" "(setq sx:type (nth (atoi $value) sx:types)) (sx:makers)")
          (action_tile "maker" "(setq sx:maker (nth (atoi $value) sx:makers)) (sx:series-list)")
          (action_tile "series" "(setq sx:series (nth (atoi $value) sx:series-list)) (sx:refresh)")
          (action_tile "search" "(setq sx:query $value) (sx:refresh)")
          (action_tile "blocks" "(setq sx:selection (atoi $value)) (sx:detail) (if (= $reason 4) (done_dialog 1))")
          (action_tile "show" "(done_dialog 1)") (action_tile "page" "(done_dialog 2)")
          (action_tile "select" "(done_dialog 3)") (action_tile "insert" "(done_dialog 4)")
          (action_tile "home" "(done_dialog 5)") (action_tile "cancel" "(done_dialog 0)")
          (setq result (start_dialog) row (nth sx:selection sx:filtered))
          (unload_dialog dlg) (vl-file-delete path)
          (cond
            ((= result 1) (sx:zoom row))
            ((= result 2) (command "_.-VIEW" "_R" (nth 6 row)))
            ((= result 3)
              (sx:zoom row) (setq b (nth 7 row))
              (setq ss (ssget "_C" (list (nth 0 b) (nth 1 b)) (list (nth 2 b) (nth 3 b)) '((0 . "INSERT") (410 . "Model"))))
              (setq selected (ssadd))
              (if ss (repeat (setq idx (sslength ss)) (setq idx (1- idx) e (ssname ss idx))
                (if (= (cdr (assoc 2 (entget e))) (nth 5 row)) (ssadd e selected))))
              (sssetfirst nil selected)
              (princ (if (> (sslength selected) 0) "\nБлок выделен: Ctrl+C / Ctrl+Shift+C для переноса в проект." "\nУ записи нет образца. Используйте «Вставить копию».")))
            ((= result 4)
              (if (setq point (getpoint "\nТочка вставки копии блока: "))
                (progn (setq attreq (getvar "ATTREQ") oldecho (getvar "CMDECHO")) (setvar "ATTREQ" 0) (setvar "CMDECHO" 0)
                  (command "_.-INSERT" (nth 5 row) "_non" point 1.0 1.0 0.0)
                  (setvar "ATTREQ" attreq) (setvar "CMDECHO" oldecho))))
            ((= result 5) (c:SXHOME))))
        (progn (if (> dlg 0) (unload_dialog dlg)) (vl-file-delete path) (princ "\nНе удалось открыть окно каталога.")))))
  (princ))
(setq sx:dialog-lines
 '("sxcat : dialog { label = \"База компоновки — поиск блока\";"
   " : row { : popup_list { key = \"type\"; label = \"Тип\"; width = 38; } : popup_list { key = \"maker\"; label = \"Производитель\"; width = 32; } }"
   " : popup_list { key = \"series\"; label = \"Серия / семейство\"; width = 90; }"
   " : edit_box { key = \"search\"; label = \"Поиск: название, артикул или код\"; edit_width = 55; }"
   " : text { key = \"count\"; width = 90; }"
   " : list_box { key = \"blocks\"; width = 100; height = 18; allow_accept = true; }"
   " : text { key = \"title\"; width = 100; }"
   " : text { key = \"model\"; width = 100; }"
   " : text { key = \"size\"; width = 100; }"
   " : text { key = \"quality\"; width = 100; }"
   " : text { key = \"definition\"; width = 100; }"
   " : row { : button { key = \"show\"; label = \"Показать блок\"; is_default = true; } : button { key = \"page\"; label = \"Показать серию\"; } : button { key = \"select\"; label = \"Выделить блок\"; } : button { key = \"insert\"; label = \"Вставить копию\"; } }"
   " : row { : button { key = \"home\"; label = \"Оглавление\"; } : button { key = \"cancel\"; label = \"Закрыть\"; is_cancel = true; } }"
   "}"))
(princ (strcat "\nКаталог загружен: " (itoa (length sx:catalog)) " блоков. Команды: SXCAT, SXHOME, SXGO."))
(princ)
