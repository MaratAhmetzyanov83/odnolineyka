;;; SX_Panel v2.07 — внутренняя компоновка электрощита из Excel.
;;; CPDRAW / CPUPDATE / CPEDIT / CPDELETE / CPEXPLODE. Самостоятельный LISP, SX_Schema не нужен.
;;; Модульные аппараты и клеммы из пользовательской базы. v2.0: ввод первым, фазы L1-L2-L3 под гребёнки,
;;; кросс-модули L/N и N/PE, монтажные провода, DIN-рейки и корпус DKC (SX_Корпуса.csv).
;;; Excel: читается «Однолинейка» и «Каталог»; пишется только лист «Сборка_щита». Слои CP_*.
(vl-load-com)
(setq cp:version "2.07" cp:app "SX_PANEL" cp:partsapp "SX_PANEL_PARTS")

;;; Unicode / CP1251: строки работают и при LISPSYS=0.
(defun cp:cp (c)
  (if (= (getvar "LISPSYS") 0)
    (cond ((and (>= c 1040) (<= c 1103)) (- c 848)) ((= c 1025) 168) ((= c 1105) 184) ((= c 8470) 185) (t c)) c))
(defun cp:ru (cs) (apply 'strcat (mapcar '(lambda (c) (chr (cp:cp c))) cs)))
(defun cp:v (v)
  (cond ((= (type v) 'VARIANT) (if (member (vlax-variant-type v) '(0 1 10)) nil (cp:v (vlax-variant-value v))))
        ((and (= (type v) 'STR) (= v "")) nil) (t v)))
(defun cp:s (v)
  (cond ((null v) "") ((= (type v) 'STR) v) ((numberp v) (rtos v 2 2)) (t "")))
(defun cp:fail (message)
  (setq cp:failure T)
  ;; AutoLISP не содержит функцию ERROR. EXIT передаёт управление обработчику.
  (princ (strcat "\nCPDRAW: " message))
  (exit))
(defun cp:dcl-file ( / file source)
  (setq file
    (cond ((and (setq source (findfile "SX_Panel.lsp"))
                (setq file (findfile (strcat (vl-filename-directory source) "/SX_Panel.dcl")))) file)
          ((and (getenv "CP_DclFile") (setq file (findfile (getenv "CP_DclFile")))) file)
          ((findfile "SX_Panel.dcl"))
          ((getfiled (cp:ru '(1059 1082 1072 1078 1080 1090 1077 32 1092 1072 1081 1083 32 1086 1082 1085 1072 32 83 88 95 80 97 110 101 108 46 100 99 108 32 1080 1079 32 1087 1072 1087 1082 1080 32 1050 1086 1084 1087 1086 1085 1086 1074 1082 1072)) "SX_Panel.dcl" "dcl" 0))))
  (if file (setenv "CP_DclFile" file))
  file)
(defun cp:num (s) (distof (vl-string-translate "," "." s) 2))
(defun cp:norm (s) (strcase (vl-string-trim " " (cp:s s))))
(defun cp:g (key) (cdr (assoc key cp:cfg)))
(defun cp:put (key val)
  (if (assoc key cp:cfg) (setq cp:cfg (subst (cons key val) (assoc key cp:cfg) cp:cfg))
    (setq cp:cfg (cons (cons key val) cp:cfg))))
(defun cp:rel (o) (if (= (type o) 'VLA-OBJECT) (vl-catch-all-apply 'vlax-release-object (list o))))
(defun cp:close-book ()
  (if (and cp:wb cp:opened) (vl-catch-all-apply 'vlax-invoke-method (list cp:wb 'Close :vlax-false)))
  (cp:rel cp:wb)
  (if (and cp:xl cp:created) (vl-catch-all-apply 'vlax-invoke-method (list cp:xl 'Quit)))
  (cp:rel cp:xl)
  (setq cp:wb nil cp:xl nil cp:opened nil cp:created nil))
(defun cp:open-book (path ro / wbs w vis)
  (cp:close-book)
  (setq cp:xl (vl-catch-all-apply 'vlax-get-object '("Excel.Application")))
  ;; v2.02: скрытый Excel скриптов (update_book, patch_*) не берём — он закрывается в любой момент (RPC недоступен).
  (if (and cp:xl (not (vl-catch-all-error-p cp:xl))
           (or (vl-catch-all-error-p (setq vis (vl-catch-all-apply 'vlax-get-property (list cp:xl 'Visible))))
               (/= (cp:v vis) :vlax-true)))
    (progn (cp:rel cp:xl) (setq cp:xl nil)))
  (if (or (null cp:xl) (vl-catch-all-error-p cp:xl)) (setq cp:xl (vlax-create-object "Excel.Application") cp:created T))
  (setq wbs (vlax-get-property cp:xl 'Workbooks))
  (vlax-for w wbs
    (if (and (null cp:wb) (= (strcase path) (strcase (vlax-get-property w 'FullName))))
      (setq cp:wb w) (cp:rel w)))
  (if (null cp:wb)
    (setq cp:wb (vlax-invoke-method wbs 'Open path :vlax-false (if ro :vlax-true :vlax-false)) cp:opened T))
  (cp:rel wbs)
  cp:wb)
(defun cp:range (sheet addr / shs sh rg vals)
  (setq shs (vlax-get-property cp:wb 'Worksheets))
  (setq sh (vl-catch-all-apply 'vlax-get-property (list shs 'Item sheet)))
  (cp:rel shs)
  (if (vl-catch-all-error-p sh) (cp:fail (strcat (cp:ru '(1053 1077 1090 32 1083 1080 1089 1090 1072 32 69 120 99 101 108 58 32)) sheet)))
  (setq rg (vlax-get-property sh 'Range addr))
  (setq vals (vl-catch-all-apply '(lambda () (vlax-safearray->list (vlax-variant-value (vlax-get-property rg 'Value2)))) nil))
  (cp:rel rg) (cp:rel sh)
  (if (vl-catch-all-error-p vals) (cp:fail (vl-catch-all-error-message vals)))
  (mapcar '(lambda (r) (mapcar 'cp:v r)) vals))
(defun cp:read-book (path /)
  (cp:open-book path T)
  (setq cp:rows (cp:range (cp:ru '(1054 1076 1085 1086 1083 1080 1085 1077 1081 1082 1072)) "A3:BY1000")
        cp:catalog (cp:range (cp:ru '(1050 1072 1090 1072 1083 1086 1075)) "A4:Q1000") cp:panels nil)
  (foreach r cp:rows (if (and (car r) (not (member (cp:s (car r)) cp:panels))) (setq cp:panels (append cp:panels (list (cp:s (car r)))))))
  (cp:read-asm)
  (cp:close-book))

;;; Аппарат: (id, ключ, модель, ширина DIN, высота, тип, строка, блок, масштаб, угол).
(defun cp:at (r c) (nth (1- c) r))
(defun cp:words (s / i ch word res)
  (setq i 1 word "")
  (while (<= i (strlen s))
    (setq ch (substr s i 1))
    (if (= ch " ") (progn (if (/= word "") (setq res (cons word res))) (setq word "")) (setq word (strcat word ch)))
    (setq i (1+ i)))
  (if (/= word "") (setq res (cons word res))) (reverse res))
(defun cp:qparts (s / toks poles amp diff tk u)
  (setq toks (cp:words (cp:s s)) poles "" amp nil diff nil)
  (foreach tk toks
    (setq u (strcase tk))
    (cond ((wcmatch u "#P,#P+N") (setq poles u))
          ((wcmatch u (strcase (cp:ru '(42 1084 1040)))) (setq diff T))
          ((null amp) (setq amp (cp:lead-num tk)))))
  (list poles amp diff))
(defun cp:qcatalog (r / parts c candidates diff qchar model)
  (setq parts (cp:qparts (cp:at r 8)) candidates nil)
  (foreach c cp:catalog
    (setq diff (= (cp:norm (nth 10 c)) (cp:norm (cp:ru '(1076 1072)))))
    (if (and (member (cp:norm (car c)) (list (cp:norm (cp:ru '(1040 1074 1090 1086 1084 1072 1090))) (cp:norm (cp:ru '(1044 1080 1092 1072 1074 1090 1086 1084 1072 1090)))))
             (= (cp:norm (nth 8 c)) (car parts))
             (numberp (nth 9 c)) (numberp (cadr parts)) (equal (nth 9 c) (cadr parts) 0.001)
             (equal diff (caddr parts)))
      (setq candidates (cons c candidates))))
  ;; При нескольких моделях не угадывать производителя/серию.
  (if (= (length candidates) 1) (car candidates)))
(defun cp:model-catalog (model / matches)
  (foreach c cp:catalog (if (= (cp:norm (nth 2 c)) (cp:norm model)) (setq matches (cons c matches))))
  (if (= (length matches) 1) (car matches)))
(defun cp:add-device (id model cat kind row / key mods)
  (setq key (strcat kind "|" (cp:norm model)) mods (if cat (nth 11 cat)))
  (if (or (not (numberp mods)) (<= mods 0)) (setq mods nil))
  (setq cp:devices (append cp:devices (list (list id key model mods (cp:g 'devh) kind row)))))
(defun cp:cable-section (text / norm at section)
  (setq norm (vl-string-translate (cp:ru '(1093 1061 88 215 44)) "xxxx." (cp:s text)) at (vl-string-search "x" norm))
  (if at (setq section (atof (substr norm (+ at 2)))))
  (if (and section (> section 0)) section))
(defun cp:cable-cores (text / norm at i ch digits count)
  (setq norm (vl-string-translate (cp:ru '(1093 1061 88 215 44)) "xxxx." (cp:s text))
        at (vl-string-search "x" norm) digits "")
  (if at
    (progn
      (setq i at)
      (while (and (> i 0) (= (substr norm i 1) " ")) (setq i (1- i)))
      (while (and (> i 0) (wcmatch (setq ch (substr norm i 1)) "#"))
        (setq digits (strcat ch digits) i (1- i)))
      (setq count (atoi digits))))
  (if (and count (> count 0)) count))
;;; v2.04: свыше 16 мм2 — винтовые KRU (35), KRUH (50…240); PE — KRUSLG до 95, выше — KRUH.
(defun cp:xt-big (size pin / s)
  (if (<= size 35.0)
    (cond ((= pin "PE") "KRUSLG-35N") ((= pin "N") "KRU-35N-BU") (t "KRU-35N"))
    (progn
      (setq s (itoa (fix size)))
      (cond ((and (= pin "PE") (<= size 95.0)) (strcat "KRUSLG-" s "N"))
            ((= pin "N") (strcat "KRUH-" s "-BU"))
            (t (strcat "KRUH-" s))))))
(defun cp:terminal-set (id r / section cores sizes size phases pins color model suffix pin items)
  (setq section (cp:cable-section (cp:at r 17)) cores (cp:cable-cores (cp:at r 17))
        sizes '(1.5 2.5 4.0 6.0 10.0 16.0 35.0 50.0 95.0 150.0 240.0))
  (if (null section) (cp:fail (strcat (cp:ru '(1053 1077 32 1085 1072 1081 1076 1077 1085 1086 32 1089 1077 1095 1077 1085 1080 1077 32 1082 1072 1073 1077 1083 1103 32 1076 1083 1103 32)) id (cp:ru '(46 32 1055 1088 1086 1074 1077 1088 1100 1090 1077 32 1089 1090 1086 1083 1073 1077 1094 32 81 46)) (cp:ru '(32 1065 1080 1090 58 32)) (cp:s (cp:g 'panel)) (cp:ru '(44 32 1082 1085 1080 1075 1072 58 32)) (vl-filename-base (cp:s (cp:g 'path))) (cp:ru '(44 32 81 58 32 171)) (cp:s (cp:at r 17)) (cp:ru '(187)))))
  (setq size (car (vl-remove-if '(lambda (n) (< n section)) sizes)))
  (if (null size) (cp:fail (strcat (cp:ru '(1044 1083 1103 32)) id (cp:ru '(32 1074 32 1073 1072 1079 1077 32 1085 1077 1090 32 1082 1083 1077 1084 1084 1099 32 1087 1086 1076 32 1089 1077 1095 1077 1085 1080 1077 32)) (cp:s section))))
  (setq phases (if (or (= (cp:at r 44) 3) (vl-string-search "," (cp:s (cp:at r 22)))) 3 1))
  (if (and (= cores 3) (<= section 2.5))
    (progn
      (setq model "VPR-2.5-3L-GY"
            items (list (list id (strcat "XT|" model) model nil nil "XT" 0))))
    (progn
      (setq pins (if (= phases 1) '("L" "N" "PE") '("L1" "L2" "L3" "N" "PE")))
      (foreach pin pins
        (setq color (cond ((= pin "N") "BU") ((= pin "PE") (if (= size 1.5) "PE" "PE-YG")) (t "GY"))
              suffix (if (member size '(1.5 2.5)) (rtos size 2 1) (itoa (fix size)))
              model (if (> size 16.0) (cp:xt-big size pin) (strcat "VPR-" suffix "-" color)))
        (setq items (append items (list (list (strcat id ":" pin) (strcat "XT|" model) model nil nil "XT" 0)))))))
  (setq cp:terminalgroups (append cp:terminalgroups (list (list id items section)))))
(defun cp:apply-terminals ( / groups group items d m bb)
  (setq cp:terminals nil groups nil)
  (foreach group cp:terminalgroups
    (setq items nil)
    (foreach d (cadr group)
      (setq m (cdr (assoc (nth 1 d) (cp:g 'sizes))))
      (if (null m) (setq m (list (nth 2 d) 1.0 0.0)))
      (setq bb (cp:measure (car m) (cadr m) (caddr m) (nth 3 m))
            d (list (car d) (nth 1 d) (nth 2 d) (- (nth 2 bb) (nth 0 bb)) (- (nth 3 bb) (nth 1 bb)) "XT" 0 (car m) (cadr m) (caddr m) (nth 3 m))
            items (append items (list d)) cp:terminals (append cp:terminals (list d))))
    (setq groups (append groups (list (list (car group) items (nth 2 group))))))
  (setq cp:terminalgroups groups))
(defun cp:cross-add ( / counts d r parts ph poles idx)
  ;; Счёт отходящих подключений по фазам + одно питающее подключение на полюс.
  (setq counts '(0 0 0 0) cp:cross-unknown 0)
  (foreach d cp:devices
    (if (= (nth 5 d) "QF")
      (progn
        (setq r (nth (- (nth 6 d) 3) cp:rows) parts (cp:qparts (cp:at r 8))
              ph (cp:norm (cp:at r 22)) poles (car parts))
        (cond ((member poles '("3P" "4P"))
               (setq counts (list (1+ (car counts)) (1+ (cadr counts)) (1+ (caddr counts)) (nth 3 counts))))
              ((member ph '("L1" "L2" "L3"))
               (setq idx (vl-position ph '("L1" "L2" "L3")))
               (setq counts (mapcar '(lambda (n j) (if (= j idx) (1+ n) n)) counts '(0 1 2 3))))
              (t ;; Без фазы не угадываем: предусматриваем подключение на каждой фазе.
               (setq cp:cross-unknown (1+ cp:cross-unknown)
                     counts (list (1+ (car counts)) (1+ (cadr counts)) (1+ (caddr counts)) (nth 3 counts)))))
        (if (member poles '("2P" "4P" "1P+N")) (setq counts (list (car counts) (cadr counts) (caddr counts) (1+ (nth 3 counts))))))))
  (setq cp:devices (append (cp:cross-devices counts) (if (cp:g 'npe) (cp:npe-devices)) cp:devices)))
(defun cp:collect (panel / selected r idx cat qid mid model n typ txt id seenq seenm seenxt k counts parts input)
  (setq cp:devices nil cp:terminals nil cp:terminalgroups nil selected nil idx 3 counts nil cp:info nil)
  (foreach r cp:rows
    (if (and (= (cp:s (car r)) panel) (numberp (cp:at r 2)) (= (cp:at r 56) 1))
      (setq selected (cons (list r idx) selected)))
    (setq idx (1+ idx)))
  (setq selected (vl-sort selected '(lambda (a b) (< (cp:at (car a) 2) (cp:at (car b) 2)))))
  (foreach rec selected
    (setq r (car rec) idx (cadr rec) input (cp:input-row-p r) qid (cp:s (cp:at r 36)))
    (if (and input (/= (cp:s (cp:at r 7)) "")) (setq qid (cp:s (cp:at r 7))))
    (if (and (/= qid "") (not (member qid seenq)))
      (progn
        (setq seenq (cons qid seenq) parts (cp:qparts (cp:at r 8)) cat (if input nil (cp:qcatalog r))
              model (if cat (cp:s (nth 2 cat)) (cp:s (cp:at r 8))))
        (cp:add-device qid model cat (if input "QS" "QF") idx)
        (foreach p (list (cons 'poles (car parts)) (cons 'amp (cadr parts)) (cons 'diff (caddr parts))
                         (cons 'phase (cp:norm (cp:at r 22))) (cons 'input input) (cons 'row idx))
          (cp:inf-put qid (car p) (cdr p)))
        (setq k 0)
        (repeat 3
          (setq typ (cp:s (cp:at r (+ 60 k))) txt (cp:s (cp:at r (+ 9 k))))
          (if (/= typ "")
            (progn
              (setq n (1+ (if (assoc typ counts) (cdr (assoc typ counts)) 0)))
              (if (assoc typ counts) (setq counts (subst (cons typ n) (assoc typ counts) counts)) (setq counts (cons (cons typ n) counts)))
              (setq id (strcat typ (itoa n)) cat (cp:model-catalog txt))
              (cp:add-device id txt cat typ idx)
              (cp:inf-put id 'parent qid)))
          (setq k (1+ k)))))
    (setq mid (cp:s (cp:at r 34)) model (cp:s (cp:at r 35)))
    (if (and (/= mid "") (/= model "") (not (member mid seenm)))
      (progn (setq seenm (cons mid seenm)) (cp:add-device mid model (cp:model-catalog model) "MODULE" idx)))
    (setq txt (cp:s (cp:at r 16)))
    (if (and (= (cp:at r 51) 1) (/= txt "") (not (member txt seenxt)))
      (progn
        (setq seenxt (cons txt seenxt)) (cp:terminal-set txt r)
        (if (/= qid "") (cp:inf-put qid 'tids (append (cp:inf qid 'tids) (list txt)))))))
  (foreach group cp:terminalgroups (setq cp:terminals (append cp:terminals (cadr group))))
  (if cp:devices (cp:cross-add))
  cp:devices)
(defun cp:apply-sizes ( / mapping metrics name scale rot)
  (setq cp:devices (mapcar '(lambda (d)
    (setq mapping (cdr (assoc (nth 1 d) (cp:g 'sizes))))
    (if mapping
      (progn
        (setq name (car mapping) scale (cadr mapping) rot (caddr mapping)
              metrics (cp:measure name scale rot (nth 3 mapping)))
        (list (nth 0 d) (nth 1 d) (nth 2 d)
              (/ (- (nth 2 metrics) (nth 0 metrics)) (cp:g 'pitch))
              (- (nth 3 metrics) (nth 1 metrics)) (nth 5 d) (nth 6 d) name scale rot (nth 3 mapping)))
      d)) cp:devices)))

;;; Проверка и раскладка до изменения чертежа.
;;; Позиция: (аппарат, номер рейки, x от начала рейки).
(defun cp:pack (devices capacity pitch / row x placed bad d width rest fit)
  (foreach d devices
    (cond ((not (numberp (nth 3 d))) (setq bad (strcat (cp:ru '(1053 1077 32 1079 1072 1076 1072 1085 1072 32 1096 1080 1088 1080 1085 1072 58 32)) (car d))))
          ((> (* (nth 3 d) pitch) (+ capacity 0.001)) (setq bad (strcat (cp:ru '(1040 1087 1087 1072 1088 1072 1090 32 1096 1080 1088 1077 32 1076 1086 1089 1090 1091 1087 1085 1086 1075 1086 32 1084 1077 1089 1090 1072 32 1085 1072 32 1088 1077 1081 1082 1077 58 32)) (car d))))))
  (if bad (list nil 0 bad)
    (progn
      (setq row 0 x 0.0 rest devices)
      (while rest
        (setq d (car rest) width (* (nth 3 d) pitch))
        (cond ((<= (+ x width) (+ capacity 0.001))
               (setq placed (cons (list d row x) placed) x (+ x width) rest (cdr rest)))
              ((and (cp:g 'dense)
                    (setq fit (vl-some '(lambda (e) (if (and (<= (+ x (* (nth 3 e) pitch)) (+ capacity 0.001))
                                                             ;; с гребёнками не рвать круг фаз
                                                             (not (and (cp:g 'comb) (cp:comb-class e)))) e)) (cdr rest))))
               (setq placed (cons (list fit row x) placed) x (+ x (* (nth 3 fit) pitch)) rest (cp:remove-first fit rest)))
              (t (setq row (1+ row) x 0.0))))
      (list (reverse placed) (if devices (1+ row) 0) nil))))
(defun cp:endcap (group / model)
  ;; KRU / KRUH / KRUSLG — закрытый корпус, торцевая крышка не нужна.
  (setq model (nth 2 (car (cadr group))))
  (if (wcmatch model "VPR-*") (cp:endcap-vpr model (cp:words (vl-string-translate "-" " " model)))))
;;; NTH от nil в AutoCAD — ошибка consp; у клемм без крышки имя "".
(defun cp:cap-name (cap) (if cap (nth 7 cap) ""))
(defun cp:endcap-vpr (model tokens / name bb)
  (setq name (strcat "D-VPR-" (cadr tokens) (if (wcmatch model "VPR-*-3L-*") "-3L" "")) bb (cp:measure name 1.0 0.0 nil))
  (list "" name name (- (nth 2 bb) (nth 0 bb)) (- (nth 3 bb) (nth 1 bb)) "CAP" 0 name 1.0 0.0 nil))
(defun cp:plan ( / usable packed maxh crossname xtrow xtx groupwidth group remaining cap lastcap closed loops)
  (setq cp:problem nil cp:positions nil cp:segs nil cp:wirelist nil cp:bomrows nil
        cp:railw (* (cp:g 'slots) (cp:g 'pitch))
        usable (* cp:railw (- 1.0 (/ (cp:g 'reserve) 100.0))))
  (if (cp:g 'comb) (cp:arrange))
  (setq packed (cp:pack cp:devices usable (cp:g 'pitch)) loops 0)
  ;; Кросс-модуль зависит от гребёнок, гребёнки — от раскладки: до трёх уточнений.
  (while (and (cp:g 'comb) (null (caddr packed)) (< loops 3))
    (setq cp:positions (car packed) loops (1+ loops))
    (cp:segments)
    (if (cp:cross-update)
      (progn (cp:arrange) (setq packed (cp:pack cp:devices usable (cp:g 'pitch))))
      (setq loops 3)))
  (cond ((null cp:devices) (setq cp:problem (cp:ru '(1059 32 1074 1099 1073 1088 1072 1085 1085 1086 1075 1086 32 1097 1080 1090 1072 32 1085 1077 1090 32 1072 1087 1087 1072 1088 1072 1090 1086 1074 32 1076 1083 1103 32 1082 1086 1084 1087 1086 1085 1086 1074 1082 1080 46))))
        ((caddr packed) (setq cp:problem (caddr packed)))
        (t (setq cp:positions (car packed))))
  (setq cp:devrows (max (fix (if (numberp (cp:g 'nrows)) (cp:g 'nrows) 0)) (cadr packed)))
  (if (cp:g 'comb) (cp:segments))
  (foreach d cp:devices
    (cond ((= (nth 5 d) "CROSS")
           (setq crossname (nth 7 d))
           (if (or (null crossname) (not (wcmatch crossname "EKF_CM_4x7,EKF_CM_4x11,EKF_CM_4x15")))
             (setq cp:problem (cp:ru '(1044 1083 1103 32 1082 1088 1086 1089 1089 45 1084 1086 1076 1091 1083 1103 32 1074 1099 1073 1077 1088 1080 1090 1077 32 69 75 70 95 67 77 95 52 120 55 44 32 69 75 70 95 67 77 95 52 120 49 49 32 1080 1083 1080 32 69 75 70 95 67 77 95 52 120 49 53 32 1080 1079 32 1074 1072 1096 1077 1081 32 1073 1072 1079 1099 46)))
             (if (< (* cp:cross-banks (1- (atoi (substr crossname 10)))) (apply 'max cp:cross-counts))
               (setq cp:problem (cp:ru '(1042 32 1074 1099 1073 1088 1072 1085 1085 1086 1084 32 1082 1088 1086 1089 1089 45 1084 1086 1076 1091 1083 1077 32 1085 1077 1076 1086 1089 1090 1072 1090 1086 1095 1085 1086 32 1087 1086 1076 1082 1083 1102 1095 1077 1085 1080 1081 46 32 1054 1076 1085 1086 32 1087 1086 1076 1082 1083 1102 1095 1077 1085 1080 1077 32 1082 1072 1078 1076 1086 1075 1086 32 1087 1086 1083 1102 1089 1072 32 1086 1089 1090 1072 1074 1083 1077 1085 1086 32 1087 1086 1076 32 1087 1080 1090 1072 1085 1080 1077 46))))))
          ((= (nth 5 d) "NPE")
           (setq crossname (nth 7 d))
           (if (or (null crossname) (not (wcmatch crossname "EKF_CM_2x7,EKF_CM_2x11,EKF_CM_2x15")))
             (setq cp:problem (cp:ru '(1044 1083 1103 32 1084 1086 1076 1091 1083 1103 32 78 47 80 69 32 1074 1099 1073 1077 1088 1080 1090 1077 32 69 75 70 95 67 77 95 50 120 55 44 32 69 75 70 95 67 77 95 50 120 49 49 32 1080 1083 1080 32 69 75 70 95 67 77 95 50 120 49 53 32 1080 1079 32 1074 1072 1096 1077 1081 32 1073 1072 1079 1099 46)))
             (if (< (* cp:npe-banks (1- (atoi (substr crossname 10)))) (car cp:npe-counts))
               (setq cp:problem (cp:ru '(1042 32 1084 1086 1076 1091 1083 1077 32 78 47 80 69 32 1085 1077 1076 1086 1089 1090 1072 1090 1086 1095 1085 1086 32 1087 1086 1076 1082 1083 1102 1095 1077 1085 1080 1081 46))))))))
  (setq cp:stage 'terminals) (cp:apply-terminals)
  (setq cp:stage 'xt-layout cp:xtpositions nil cp:xtrows 0 cp:caps nil xtrow 0 xtx 0.0 remaining cp:terminalgroups closed T)
  (while remaining
    (setq group (car remaining) cap (cp:endcap group)
          groupwidth (apply '+ (mapcar '(lambda (d) (nth 3 d)) (cadr group))))
    (if (> (+ groupwidth (if cap (nth 3 cap) 0.0)) cp:railw) (setq cp:problem (strcat (cp:ru '(1053 1072 1073 1086 1088 32 1082 1083 1077 1084 1084 32)) (car group) (cp:ru '(32 1089 32 1079 1072 1075 1083 1091 1096 1082 1086 1081 32 1096 1080 1088 1077 32 1088 1103 1076 1072 46)))))
    (if (> (+ xtx groupwidth (if cap (nth 3 cap) 0.0)) cp:railw)
      (progn
        (if (and (not closed) lastcap)
          (setq cp:xtpositions (append cp:xtpositions (list (list lastcap xtrow xtx))) cp:caps (cons lastcap cp:caps)))
        (setq xtrow (1+ xtrow) xtx 0.0)))
    (foreach d (cadr group)
      (setq cp:xtpositions (append cp:xtpositions (list (list d xtrow xtx))) xtx (+ xtx (nth 3 d))))
    (setq closed (or (null (cdr remaining))
                     (/= (cp:cap-name cap) (cp:cap-name (cp:endcap (cadr remaining))))))
    (if (and closed cap)
      (setq cp:xtpositions (append cp:xtpositions (list (list cap xtrow xtx))) cp:caps (cons cap cp:caps) xtx (+ xtx (nth 3 cap))))
    (setq lastcap cap remaining (cdr remaining)))
  (if cp:terminals (setq cp:xtrows (1+ xtrow)))
  (setq cp:totalrows (+ cp:devrows cp:xtrows)
        maxh (apply 'max (append (list (cp:g 'devh)) (mapcar '(lambda (d) (nth 4 d)) cp:terminals) (mapcar '(lambda (d) (nth 4 d)) cp:caps) (mapcar '(lambda (d) (nth 4 d)) cp:devices)))
        cp:maxh maxh
        cp:rowpitch (if (cp:g 'railpitch) (cp:g 'railpitch) (+ maxh (cp:g 'gap)))
        cp:rowtop (+ (/ maxh 2.0) (* (1- cp:totalrows) cp:rowpitch)))
  (cp:put 'w cp:railw)
  (cp:put 'h (+ maxh (* (1- cp:totalrows) cp:rowpitch)))
  (setq cp:stage 'posmap) (if (null cp:problem) (cp:posmap))
  (setq cp:stage 'wires) (if (and (null cp:problem) (cp:g 'wiring)) (cp:wires))
  (setq cp:stage 'case cp:case (if (null cp:problem) (cp:case-pick)))
  (setq cp:stage 'bom) (if (and (null cp:problem) (cp:g 'wiring)) (cp:bom))
  (null cp:problem))

;;; ===== v2.0: ток, полюса, фазы =====
;;; Ведущее число токена: «С16А» -> 16, «80А» -> 80, «QS» -> nil.
(defun cp:lead-num (s / i ch out started stop)
  (setq i 1 out "" s (cp:s s))
  (while (and (<= i (strlen s)) (not stop))
    (setq ch (substr s i 1))
    (cond ((wcmatch ch "#") (setq out (strcat out ch) started T))
          ((and started (member ch '("." ","))) (setq out (strcat out ".")))
          (started (setq stop T)))
    (setq i (1+ i)))
  (if (/= out "") (distof (vl-string-right-trim "." out) 2)))
;;; Характеристика B/C/D; кириллица В/С/Д -> латиница.
(defun cp:curve (rating / tk c res)
  (foreach tk (cp:words (cp:s rating))
    (if (and (null res) (> (strlen tk) 1) (wcmatch (substr tk 2 1) "#"))
      (progn
        (setq c (ascii (substr tk 1 1)))
        (setq res (cond ((member c '(66 98 1042 1074)) "B") ((member c '(67 99 1057 1089)) "C")
                        ((member c '(68 100 1044 1076)) "D"))))))
  res)
;;; Сведения об аппарате: id -> ((ключ . значение) ...).
(defun cp:inf (id key) (cdr (assoc key (cdr (assoc id cp:info)))))
(defun cp:inf-put (id key val / rec)
  (setq rec (cdr (assoc id cp:info)))
  (setq rec (if (assoc key rec) (subst (cons key val) (assoc key rec) rec) (cons (cons key val) rec)))
  (setq cp:info (cons (cons id rec) (vl-remove-if '(lambda (p) (equal (car p) id)) cp:info))))
(defun cp:input-row-p (r / code line word)
  (setq code (cp:norm (cp:at r 38)) line (cp:norm (cp:at r 18)) word (cp:norm (cp:ru '(1042 1074 1086 1076))))
  (or (= code word) (wcmatch line (strcat word ".*"))))
(defun cp:phase-ok (p) (member p '("L1" "L2" "L3")))
(defun cp:next-phase (p) (cadr (member p '("L1" "L2" "L3" "L1"))))
;;; Класс гребёнки: 1P, 1PN (1P+N, 2P, дифавтомат 1P), 3P, 4P.
(defun cp:class (d / poles)
  (if (and (= (nth 5 d) "QF") (setq poles (cp:inf (car d) 'poles)))
    (cond ((= poles "3P") "3P") ((= poles "4P") "4P")
          ((member poles '("2P" "1P+N")) "1PN")
          ((= poles "1P") (if (cp:inf (car d) 'diff) "1PN" "1P")))))
(defun cp:comb-class (d / cls need)
  (setq cls (cp:class d) need (cdr (assoc cls '(("1P" . 1.0) ("1PN" . 2.0) ("3P" . 3.0) ("4P" . 4.0)))))
  (if (and cls need (numberp (nth 3 d)) (equal (nth 3 d) need 0.1)
           (or (member cls '("3P" "4P")) (cp:inf (car d) 'aphase)))
    cls))
(defun cp:class-name (cls) (if (= cls "1PN") "1P+N" cls))
(defun cp:has-n (d / poles)
  (setq poles (cp:inf (car d) 'poles))
  (or (member poles '("2P" "4P" "1P+N")) (and (= poles "1P") (cp:inf (car d) 'diff))))
(defun cp:three-p (d) (member (cp:inf (car d) 'poles) '("3P" "4P")))
;;; Фазы для счёта кросс-модуля: без фазы — на каждой фазе (как раньше).
(defun cp:dev-phases (d / p)
  (setq p (cond ((cp:inf (car d) 'aphase)) ((cp:inf (car d) 'phase))))
  (cond ((cp:three-p d) '("L1" "L2" "L3")) ((cp:phase-ok p) (list p)) (t '("L1" "L2" "L3"))))
;;; Фазы для проводов: однополюсный без фазы — L1.
(defun cp:wire-phases (d / p)
  (setq p (cond ((cp:inf (car d) 'aphase)) ((cp:inf (car d) 'phase))))
  (cond ((cp:three-p d) '("L1" "L2" "L3")) ((cp:phase-ok p) (list p)) (t '("L1"))))
;;; Порядок: ввод, кросс-модули, 3P/4P, 1P+N, 1P (по кругу L1-L2-L3), прочие QF, аппараты и модули.
(defun cp:cycle (lst / qs wild k p pick j out cyc)
  (setq cyc '("L1" "L2" "L3") qs (list (list "L1") (list "L2") (list "L3")) k 0)
  (foreach d lst
    (setq p (cp:inf (car d) 'phase))
    (if (cp:phase-ok p) (setq qs (subst (append (assoc p qs) (list d)) (assoc p qs) qs))
      (setq wild (append wild (list d)))))
  (while (or (cdr (assoc "L1" qs)) (cdr (assoc "L2" qs)) (cdr (assoc "L3" qs)) wild)
    (setq p (nth (rem k 3) cyc))
    (cond ((cdr (assoc p qs)) (setq pick (cadr (assoc p qs)) qs (subst (cons p (cddr (assoc p qs))) (assoc p qs) qs)))
          (wild (setq pick (car wild) wild (cdr wild)) (cp:inf-put (car pick) 'assumed T))
          (t (setq j 1)
             (while (not (cdr (assoc (nth (rem (+ k j) 3) cyc) qs))) (setq j (1+ j)))
             (setq k (+ k j) p (nth (rem k 3) cyc)
                   pick (cadr (assoc p qs)) qs (subst (cons p (cddr (assoc p qs))) (assoc p qs) qs))))
    (cp:inf-put (car pick) 'aphase p)
    (setq out (cons pick out) k (1+ k)))
  (reverse out))
(defun cp:arrange ( / head cross npe c3 c4 c1n c1 qx rest cls)
  (foreach d cp:devices
    (setq cls (cp:class d))
    (cond ((= (nth 5 d) "QS") (setq head (cons d head)))
          ((= (nth 5 d) "CROSS") (setq cross (cons d cross)))
          ((= (nth 5 d) "NPE") (setq npe (cons d npe)))
          ((= cls "3P") (setq c3 (cons d c3)))
          ((= cls "4P") (setq c4 (cons d c4)))
          ((= cls "1PN") (setq c1n (cons d c1n)))
          ((= cls "1P") (setq c1 (cons d c1)))
          ((= (nth 5 d) "QF") (setq qx (cons d qx)))
          (t (setq rest (cons d rest)))))
  (setq cp:devices (append (reverse head) (reverse cross) (reverse npe) (reverse c3) (reverse c4)
                           (cp:cycle (reverse c1n)) (cp:cycle (reverse c1)) (reverse qx) (reverse rest))))
;;; ===== Кросс-модули =====
(defun cp:cnt+ (counts idx) (mapcar '(lambda (n j) (if (= j idx) (1+ n) n)) counts '(0 1 2 3)))
(defun cp:ways (need) (cond ((<= need 6) 7) ((<= need 10) 11) (t 15)))
(defun cp:banks (need ways) (max 1 (fix (+ (/ (float need) (1- ways)) 0.999999))))
(defun cp:cross-devices (counts / need ways banks name k res)
  (setq need (apply 'max counts) ways (cp:ways need) banks (cp:banks need ways)
        name (strcat "EKF_CM_4x" (itoa ways)) k 1
        cp:cross-counts counts cp:cross-banks banks cp:cross-ways ways)
  (repeat banks
    (setq res (append res (list (list (strcat "XRM" (itoa k)) (strcat "CROSS|" name) name nil (cp:g 'devh) "CROSS" 0))) k (1+ k)))
  res)
;;; N и PE: размер — по N отходящих 1P; ряд PE берёт сколько вместит, остальные PE — на шину PE.
(defun cp:npe-devices ( / nn pe need ways banks name k res)
  (setq nn 0 pe 0)
  (foreach d cp:devices
    (if (and (= (nth 5 d) "QF") (= (cp:inf (car d) 'poles) "1P") (not (cp:has-n d))) (setq nn (1+ nn))))
  (setq pe (length cp:terminalgroups) need nn ways (cp:ways need) banks (cp:banks need ways)
        name (strcat "EKF_CM_2x" (itoa ways)) k 1 cp:npe-counts (list nn pe) cp:npe-banks banks cp:npe-ways ways)
  (if (> (max nn pe) 0)
    (repeat banks
      (setq res (append res (list (list (strcat "XNP" (itoa k)) (strcat "NPE|" name) name nil (cp:g 'devh) "NPE" 0))) k (1+ k))))
  res)
;;; С гребёнками: одно подключение на фазу гребёнки, N — для гребёнок 1P+N и 4P.
(defun cp:comb-counts ( / counts ph)
  (setq counts '(0 0 0 0))
  (foreach s cp:segs
    (foreach ph (cp:seg-phases s) (setq counts (cp:cnt+ counts (vl-position ph '("L1" "L2" "L3")))))
    (if (member (car s) '("1PN" "4P")) (setq counts (cp:cnt+ counts 3))))
  (foreach d cp:devices
    (if (and (= (nth 5 d) "QF") (not (cp:seg-of (car d))))
      (progn
        (foreach ph (cp:dev-phases d) (setq counts (cp:cnt+ counts (vl-position ph '("L1" "L2" "L3")))))
        (if (or (cp:has-n d) (and (not (cp:g 'npe)) (= (cp:inf (car d) 'poles) "1P")))
          (setq counts (cp:cnt+ counts 3))))))
  counts)
(defun cp:size-one (d / mapping metrics)
  (setq mapping (cdr (assoc (nth 1 d) (cp:g 'sizes))))
  (if (null mapping) (setq mapping (list (nth 2 d) 1.0 0.0 nil)))
  (setq metrics (cp:measure (car mapping) (cadr mapping) (caddr mapping) (nth 3 mapping)))
  (list (nth 0 d) (nth 1 d) (nth 2 d) (/ (- (nth 2 metrics) (nth 0 metrics)) (cp:g 'pitch))
        (- (nth 3 metrics) (nth 1 metrics)) (nth 5 d) (nth 6 d) (car mapping) (cadr mapping) (caddr mapping) (nth 3 mapping)))
;;; Пересчёт фазного кросс-модуля по гребёнкам. T — состав изменился.
(defun cp:cross-update ( / old new)
  (setq old (vl-remove-if-not '(lambda (d) (= (nth 5 d) "CROSS")) cp:devices)
        new (cp:cross-devices (cp:comb-counts)))
  (if (and (= (length old) (length new)) (= (nth 2 (car old)) (nth 2 (car new)))) nil
    (progn
      (setq cp:devices (append (mapcar 'cp:size-one new) (vl-remove-if '(lambda (d) (= (nth 5 d) "CROSS")) cp:devices)))
      T)))
;;; ===== Раскладка =====
(defun cp:remove-first (e lst)
  (cond ((null lst) nil) ((eq e (car lst)) (cdr lst)) (t (cons (car lst) (cp:remove-first e (cdr lst))))))
;;; Отрезки гребёнок: подряд на одной рейке, один класс, фазы по кругу. Отрезок — от двух аппаратов.
;;; Отрезок: (класс рейка x0 x1 (id ...) модулей).
(defun cp:segments ( / segs cur d row x cls ok)
  (foreach pos cp:positions
    (setq d (car pos) row (cadr pos) x (caddr pos) cls (cp:comb-class d))
    (setq ok (and cur cls (= cls (car cur)) (= row (cadr cur)) (equal x (nth 3 cur) 0.5)
                  (or (member cls '("3P" "4P"))
                      (= (cp:inf (car d) 'aphase) (cp:next-phase (cp:inf (last (nth 4 cur)) 'aphase))))))
    (if ok
      (setq cur (list (car cur) (cadr cur) (caddr cur) (+ x (* (nth 3 d) (cp:g 'pitch)))
                      (append (nth 4 cur) (list (car d))) (+ (nth 5 cur) (nth 3 d))))
      (progn
        (if (and cur (> (length (nth 4 cur)) 1)) (setq segs (cons cur segs)))
        (setq cur (if cls (list cls row x (+ x (* (nth 3 d) (cp:g 'pitch))) (list (car d)) (nth 3 d)))))))
  (if (and cur (> (length (nth 4 cur)) 1)) (setq segs (cons cur segs)))
  (setq cp:segs (reverse segs)))
(defun cp:seg-of (id) (vl-some '(lambda (s) (if (member id (nth 4 s)) s)) cp:segs))
(defun cp:seg-phases (s / res p)
  (if (member (car s) '("3P" "4P")) '("L1" "L2" "L3")
    (progn
      (foreach id (nth 4 s) (if (and (setq p (cp:inf id 'aphase)) (not (member p res))) (setq res (cons p res))))
      (vl-sort res '<))))
;;; ===== Монтажные провода =====
;;; Настройки листа «Сборка_щита» (или по умолчанию).
(defun cp:asm-defaults ()
  (list (cons 'colors (list (cons "L1" (cp:ru '(1073 1077 1083 1099 1081))) (cons "L2" (cp:ru '(1095 1077 1088 1085 1099 1081))) (cons "L3" (cp:ru '(1082 1088 1072 1089 1085 1099 1081)))
                            (cons "N" (cp:ru '(1089 1080 1085 1080 1081))) (cons "PE" (cp:ru '(1046 47 1047)))))
        (cons 'brand (cp:ru '(1055 1091 1043 1042))) (cons 'reserve 150.0) (cons 'pct 10.0) (cons 'round 1.0)
        (cons 'rule '((10.0 . 1.5) (16.0 . 2.5) (25.0 . 4.0) (32.0 . 6.0) (40.0 . 10.0) (63.0 . 16.0)
                      (80.0 . 25.0) (100.0 . 35.0) (125.0 . 50.0) (160.0 . 70.0) (200.0 . 95.0) (250.0 . 120.0)))))
(defun cp:asm-get (key / v)
  (setq v (cdr (assoc key cp:asm)))
  (if (null v) (cdr (assoc key (cp:asm-defaults))) v))
(defun cp:color (cnd / v) (if (setq v (cdr (assoc cnd (cp:asm-get 'colors)))) v cnd))
(defun cp:section (amp / rule hit)
  (setq rule (cp:asm-get 'rule))
  (if (and (numberp amp) (> amp 0))
    (if (setq hit (vl-some '(lambda (p) (if (<= amp (+ (car p) 0.001)) p)) rule)) (cdr hit) (cdr (last rule)))
    (cdar rule)))
(defun cp:amp0 (id / a) (if (numberp (setq a (cp:inf id 'amp))) a 0.0))
;;; Точки: (id x-лево y-центр ширина высота) для аппаратов и клемм.
(defun cp:posmap ( / d)
  (setq cp:posmapl nil)
  (foreach pos cp:positions
    (setq d (car pos))
    (setq cp:posmapl (cons (list (car d) (caddr pos) (cp:yc (cadr pos)) (* (nth 3 d) (cp:g 'pitch)) (nth 4 d)) cp:posmapl)))
  (foreach pos cp:xtpositions
    (setq d (car pos))
    (if (/= (nth 5 d) "CAP")
      (setq cp:posmapl (cons (list (car d) (caddr pos) (cp:yc (+ cp:devrows (cadr pos))) (nth 3 d) (nth 4 d)) cp:posmapl)))))
(defun cp:pt (id where / p)
  (if (setq p (assoc id cp:posmapl))
    (list (+ (nth 1 p) (/ (nth 3 p) 2.0))
          (cond ((= where 'top) (+ (nth 2 p) (/ (nth 4 p) 2.0))) ((= where 'bot) (- (nth 2 p) (/ (nth 4 p) 2.0))) (t (nth 2 p))))))
(defun cp:xt-pt (tid pin / p)
  (setq p (cond ((assoc (strcat tid ":" pin) cp:posmapl) (strcat tid ":" pin))
                ((and (cp:phase-ok pin) (assoc (strcat tid ":L") cp:posmapl)) (strcat tid ":L"))
                ((assoc tid cp:posmapl) tid)))
  (if p (cp:pt p 'top)))
(defun cp:wire (from to cnd sec p1 p2)
  (if (and p1 p2)
    (setq cp:wirelist (cons (list from to cnd (cp:color cnd) sec
                                  (+ (abs (- (car p1) (car p2))) (abs (- (cadr p1) (cadr p2))) (cp:asm-get 'reserve)))
                            cp:wirelist))))
(defun cp:wires ( / xrm xnp id sec phs n ids amp prev chain src)
  (setq cp:wirelist nil
        xrm (car (car (vl-remove-if-not '(lambda (d) (= (nth 5 d) "CROSS")) cp:devices)))
        xnp (car (car (vl-remove-if-not '(lambda (d) (= (nth 5 d) "NPE")) cp:devices))))
  ;; Ввод -> кросс-модуль; N кросс-модуля -> модуль N/PE.
  (foreach d cp:devices
    (if (= (nth 5 d) "QS")
      (progn
        (setq id (car d) sec (cp:section (cp:inf id 'amp)))
        (if xrm
          (progn
            (foreach ph (cp:wire-phases d) (cp:wire id xrm ph sec (cp:pt id 'bot) (cp:pt xrm 'mid)))
            (if (cp:has-n d) (cp:wire id xrm "N" sec (cp:pt id 'bot) (cp:pt xrm 'mid)))
            (if xnp (cp:wire xrm xnp "N" sec (cp:pt xrm 'mid) (cp:pt xnp 'mid))))))))
  ;; Кросс-модуль -> гребёнки: ток — сумма номиналов фазы, не больше 63 А.
  (if xrm
    (foreach s cp:segs
      (foreach ph (cp:seg-phases s)
        (setq ids (if (member (car s) '("3P" "4P")) (nth 4 s) (vl-remove-if-not '(lambda (i) (= (cp:inf i 'aphase) ph)) (nth 4 s)))
              amp (min 63.0 (apply '+ (mapcar 'cp:amp0 ids))))
        (cp:wire xrm (car ids) ph (cp:section amp) (cp:pt xrm 'mid) (cp:pt (car ids) 'top)))
      (if (member (car s) '("1PN" "4P"))
        (cp:wire xrm (car (nth 4 s)) "N" (cp:section (min 63.0 (apply '+ (mapcar 'cp:amp0 (nth 4 s)))))
                 (cp:pt xrm 'mid) (cp:pt (car (nth 4 s)) 'top)))))
  ;; Отходящие: питание без гребёнки, цепочка аппаратов, клеммы L/N/PE.
  (foreach d cp:devices
    (if (= (nth 5 d) "QF")
      (progn
        (setq id (car d) sec (cp:section (cp:inf id 'amp)) phs (cp:wire-phases d) n (cp:has-n d))
        (if (and xrm (not (cp:seg-of id)))
          (progn
            (foreach ph phs (cp:wire xrm id ph sec (cp:pt xrm 'mid) (cp:pt id 'top)))
            (if n (cp:wire xrm id "N" sec (cp:pt xrm 'mid) (cp:pt id 'top)))))
        (setq prev id chain (mapcar 'car (vl-remove-if-not '(lambda (e) (= (cp:inf (car e) 'parent) id)) cp:devices)))
        (foreach a chain
          (foreach ph phs (cp:wire prev a ph sec (cp:pt prev 'bot) (cp:pt a 'top)))
          (if n (cp:wire prev a "N" sec (cp:pt prev 'bot) (cp:pt a 'top)))
          (setq prev a))
        (foreach tid (cp:inf id 'tids)
          (foreach ph phs (cp:wire prev tid ph sec (cp:pt prev 'bot) (cp:xt-pt tid ph)))
          (setq src (cond (n prev) (xnp xnp) (t xrm)))
          (if src (cp:wire src tid "N" sec (if n (cp:pt prev 'bot) (cp:pt src 'mid)) (cp:xt-pt tid "N")))
          (if xnp (cp:wire xnp tid "PE" sec (cp:pt xnp 'mid) (cp:xt-pt tid "PE")))))))
  (setq cp:wirelist (reverse cp:wirelist)))
;;; ===== Итог для спецификации =====
(defun cp:ceil (x) (if (equal x (fix x) 0.000001) (fix x) (1+ (fix x))))
(defun cp:xnorm (s) (strcase (vl-string-translate (cp:ru '(1093 1061)) "xx" (cp:s s)) T))
(defun cp:cat-find (cat pred) (vl-some '(lambda (c) (if (and (= (cp:norm (car c)) (cp:norm cat)) (apply pred (list c))) c)) cp:catalog))
(defun cp:bom-add (kind cat name model qty unit)
  (setq cp:bomrows (append cp:bomrows
    (list (list kind (if cat (cp:s (nth 6 cat)) name) (if cat (cp:s (nth 2 cat)) model) qty unit
                (if cat (cp:ru '(1076 1072)) (cp:ru '(1085 1077 1090 32 8212 32 1076 1086 1073 1072 1074 1100 1090 1077 32 1089 1090 1088 1086 1082 1091))))))))
(defun cp:bom ( / groups key hit len qty cat cls mods cnt total name names)
  (setq cp:bomrows nil)
  ;; Провода: сечение + цвет.
  (foreach w cp:wirelist
    (setq key (list (nth 4 w) (nth 3 w)))
    (if (setq hit (assoc key groups)) (setq groups (subst (cons key (+ (cdr hit) (nth 5 w))) hit groups))
      (setq groups (append groups (list (cons key (nth 5 w)))))))
  (setq groups (vl-sort groups '(lambda (a b) (< (caar a) (caar b)))))
  (foreach g groups
    (setq len (/ (* (cdr g) (+ 1.0 (/ (cp:asm-get 'pct) 100.0))) 1000.0)
          qty (* (cp:ceil (/ len (cp:asm-get 'round))) (cp:asm-get 'round))
          cat (cp:cat-find (cp:ru '(1055 1088 1086 1074 1086 1076)) '(lambda (c) (and (equal (cp:lead-num (nth 2 c)) (caar g) 0.01)
                                                          (vl-string-search (cadar g) (cp:s (nth 6 c)))))))
    (cp:bom-add (cp:ru '(1055 1088 1086 1074 1086 1076)) cat (strcat (cp:ru '(1055 1088 1086 1074 1086 1076 32)) (cp:asm-get 'brand) " " (rtos (caar g) 2 1) (cp:ru '(32 1082 1074 46 32 1084 1084 44 32)) (cadar g))
                (strcat (cp:asm-get 'brand) " " (rtos (caar g) 2 1)) qty (cp:ru '(1084))))
  ;; Гребёнки: длина по модулям, отрезки режутся из шины каталога (столбец L — модулей в шине).
  (foreach cls '("1P" "1PN" "3P" "4P")
    (setq mods 0 cnt 0)
    (foreach s cp:segs (if (= (car s) cls) (setq mods (+ mods (fix (+ (nth 5 s) 0.5))) cnt (1+ cnt))))
    (if (> cnt 0)
      (progn
        (setq cat (cp:cat-find (cp:ru '(1064 1080 1085 1099)) '(lambda (c) (= (cp:norm (nth 8 c)) (cp:class-name cls))))
              total (if (and cat (numberp (nth 11 cat)) (> (nth 11 cat) 0)) (nth 11 cat) 56))
        (cp:bom-add (cp:ru '(1064 1080 1085 1099)) cat (strcat (cp:ru '(1064 1080 1085 1072 32 1089 1086 1077 1076 1080 1085 1080 1090 1077 1083 1100 1085 1072 1103 32 80 73 78 32)) (cp:class-name cls) " (" (itoa mods) (cp:ru '(32 1084 1086 1076 46 41)))
                    (strcat "PIN " (cp:class-name cls)) (cp:ceil (/ (float mods) total)) (cp:ru '(1096 1090 46)))
        (setq cnt (* 2 cnt) cat (cp:cat-find (cp:ru '(1064 1080 1085 1099)) '(lambda (c) (= (cp:norm (nth 8 c)) (cp:norm (cp:ru '(1079 1072 1075 1083 1091 1096 1082 1072)))))))
        (cp:bom-add (cp:ru '(1064 1080 1085 1099)) cat (cp:ru '(1047 1072 1075 1083 1091 1096 1082 1072 32 1090 1086 1088 1094 1077 1074 1072 1103 32 1076 1083 1103 32 1096 1080 1085 1099 32 80 73 78)) (cp:ru '(1079 1072 1075 1083 1091 1096 1082 1072 32 80 73 78)) cnt (cp:ru '(1096 1090 46))))))
  ;; Кросс-модули по блоку.
  (foreach d cp:devices
    (if (member (nth 5 d) '("CROSS" "NPE"))
      (setq name (if (nth 7 d) (nth 7 d) (nth 2 d))
            names (if (assoc name names) (subst (cons name (1+ (cdr (assoc name names)))) (assoc name names) names)
                    (append names (list (cons name 1)))))))
  (foreach p names
    (setq key (substr (car p) 8)
          cat (cp:cat-find (cp:ru '(1064 1080 1085 1099)) '(lambda (c) (vl-string-search key (cp:xnorm (strcat (cp:s (nth 2 c)) " " (cp:s (nth 6 c))))))))
    (cp:bom-add (cp:ru '(1064 1080 1085 1099)) cat (strcat (cp:ru '(1050 1088 1086 1089 1089 45 1084 1086 1076 1091 1083 1100 32)) key) (car p) (cdr p) (cp:ru '(1096 1090 46))))
  ;; PE сверх ряда PE модуля N/PE — на шину PE (столбец L «Каталога» — подключений в шине).
  (setq cnt (- (if cp:npe-counts (cadr cp:npe-counts) 0)
               (if (vl-some '(lambda (d) (= (nth 5 d) "NPE")) cp:devices) (* cp:npe-banks (1- cp:npe-ways)) 0)))
  (if (> cnt 0)
    (progn
      (setq cat (cp:cat-find (cp:ru '(1064 1080 1085 1099)) '(lambda (c) (= (cp:norm (nth 8 c)) "PE")))
            total (if (and cat (numberp (nth 11 cat)) (> (nth 11 cat) 0)) (nth 11 cat) (1+ cnt)))
      (cp:bom-add (cp:ru '(1064 1080 1085 1099)) cat (strcat (cp:ru '(1064 1080 1085 1072 32 80 69 32 1085 1072 32 1080 1079 1086 1083 1103 1090 1086 1088 1072 1093 44 32 1087 1086 1076 1082 1083 1102 1095 1077 1085 1080 1081 58 32)) (itoa (1+ cnt))) (cp:ru '(1096 1080 1085 1072 32 80 69))
                  (cp:ceil (/ (float (1+ cnt)) total)) (cp:ru '(1096 1090 46)))))
  ;; Корпус.
  (if cp:case
    (progn
      (setq cat (cp:cat-find (cp:ru '(1050 1086 1088 1087 1091 1089)) '(lambda (c) (= (cp:norm (nth 2 c)) (cp:norm (nth 1 cp:case))))))
      (cp:bom-add (cp:ru '(1050 1086 1088 1087 1091 1089)) cat (nth 2 cp:case) (nth 1 cp:case) 1 (cp:ru '(1096 1090 46)))))
  cp:bomrows)
;;; ===== Корпус DKC (SX_Корпуса.csv рядом с LISP) =====
(defun cp:read-utf8 (path / st txt)
  (setq st (vlax-create-object "ADODB.Stream"))
  (setq txt (vl-catch-all-apply
    '(lambda ()
       (vlax-put-property st 'Type 2) (vlax-put-property st 'Charset "utf-8")
       ;; vlax-invoke: у Open и ReadText необязательные параметры.
       (vlax-invoke st 'Open) (vlax-invoke st 'LoadFromFile path)
       (vlax-invoke st 'ReadText -1))))
  (vl-catch-all-apply 'vlax-invoke (list st 'Close)) (cp:rel st)
  (if (vl-catch-all-error-p txt) nil txt))
(defun cp:split (s sep / res at)
  (while (setq at (vl-string-search sep s)) (setq res (cons (substr s 1 at) res) s (substr s (+ at 1 (strlen sep)))))
  (reverse (cons s res)))
(defun cp:case-file ( / base)
  (setq base (cond ((findfile "SX_Panel.lsp")) ((getenv "CP_DclFile"))))
  (if base (findfile (strcat (vl-filename-directory base) (cp:ru '(47 83 88 95 1050 1086 1088 1087 1091 1089 1072 46 99 115 118))))))
(defun cp:cases ( / path txt line f res)
  (if (null cp:case-cache)
    (if (and (setq path (cp:case-file)) (setq txt (cp:read-utf8 path)))
      (progn
        (foreach line (cp:split (vl-string-translate (chr 13) " " txt) "\n")
          (setq line (vl-string-trim " " line) f (cp:split line ";"))
          (if (and (> (length f) 13) (/= (substr line 1 1) "#") (cp:num (nth 5 f)) (cp:num (nth 6 f)))
            (setq res (cons (list (nth 0 f) (nth 1 f) (nth 2 f) (nth 3 f) (nth 4 f)
                                  (cp:num (nth 5 f)) (cp:num (nth 6 f)) (cp:num (nth 7 f)) (cp:num (nth 8 f)) (cp:num (nth 9 f))
                                  (cp:num (nth 10 f)) (cp:num (nth 11 f)) (cp:num (nth 12 f)) (cp:num (nth 13 f))) res))))
        (setq cp:case-cache (reverse res)))))
  cp:case-cache)
;;; Запись: (серия артикул наименование тип установка Ш В Г рядов модулей секций шаг короб поле).
(defun cp:case-fits (c / duct field)
  (setq duct (if (nth 12 c) (nth 12 c) 0.0) field (if (nth 13 c) (nth 13 c) 0.0))
  (if (= (nth 3 c) "MOD")
    (and (nth 8 c) (nth 9 c) (>= (nth 8 c) cp:totalrows) (>= (nth 9 c) (cp:g 'slots)))
    (and (>= (- (nth 5 c) (* 2 field) (* 2 duct)) (+ cp:railw 10.0))
         (>= (- (nth 6 c) (* 2 field)) (* cp:totalrows cp:rowpitch)))))
(defun cp:case-pick ( / best)
  (setq cp:case-note nil)
  (cond ((not (cp:g 'rails)) nil)
        ((= (vl-string-trim " " (cp:s (cp:g 'case))) "-") nil)
        ((setq best (cp:case-pick1 (cp:g 'caseseries))) best)
        ((/= (cp:norm (cp:g 'caseseries)) "")
         (if (setq best (cp:case-pick1 ""))
           (setq cp:case-note (strcat (cp:ru '(1042 32 1089 1077 1088 1080 1080 32)) (cp:s (cp:g 'caseseries)) (cp:ru '(32 1082 1086 1088 1087 1091 1089 32 1085 1077 32 1087 1086 1076 1093 1086 1076 1080 1090 44 32 1074 1079 1103 1090 32 1076 1088 1091 1075 1086 1081 46))))
           (setq cp:case-note (cp:ru '(1055 1086 1076 1093 1086 1076 1103 1097 1077 1075 1086 32 1082 1086 1088 1087 1091 1089 1072 32 1074 32 83 88 95 1050 1086 1088 1087 1091 1089 1072 46 99 115 118 32 1085 1077 1090 46))))
         best)
        (t (setq cp:case-note (cp:ru '(1055 1086 1076 1093 1086 1076 1103 1097 1077 1075 1086 32 1082 1086 1088 1087 1091 1089 1072 32 1074 32 83 88 95 1050 1086 1088 1087 1091 1089 1072 46 99 115 118 32 1085 1077 1090 46))) nil)))
(defun cp:case-pick1 (ser / mode series best area c)
  (setq mode (vl-string-trim " " (cp:s (cp:g 'case))) series (cp:norm ser))
  (cond ((/= mode "") (vl-some '(lambda (c) (if (= (cp:norm (nth 1 c)) (cp:norm mode)) c)) (cp:cases)))
        (t (foreach c (cp:cases)
             (if (and (or (= series "") (= (cp:norm (car c)) series)) (cp:case-fits c)
                      (or (null best) (< (* (nth 5 c) (nth 6 c)) area)
                          (and (equal (* (nth 5 c) (nth 6 c)) area 0.01) (< (if (nth 7 c) (nth 7 c) 0) (if (nth 7 best) (nth 7 best) 0)))))
               (setq best c area (* (nth 5 c) (nth 6 c)))))
           best)))
;;; ===== Лист «Сборка_щита» =====
(defun cp:asm-name () (cp:ru '(1057 1073 1086 1088 1082 1072 95 1097 1080 1090 1072)))
(defun cp:sheet-soft (name / shs sh)
  (setq shs (vlax-get-property cp:wb 'Worksheets) sh (vl-catch-all-apply 'vlax-get-property (list shs 'Item name)))
  (cp:rel shs)
  (if (vl-catch-all-error-p sh) nil sh))
(defun cp:sheet-values (sh addr / rg vals)
  (setq rg (vlax-get-property sh 'Range addr))
  (setq vals (vl-catch-all-apply '(lambda () (vlax-safearray->list (vlax-variant-value (vlax-get-property rg 'Value2)))) nil))
  (cp:rel rg)
  (if (vl-catch-all-error-p vals) nil (mapcar '(lambda (r) (mapcar 'cp:v r)) vals)))
(defun cp:read-asm ( / sh vals rule colors)
  (setq cp:asm nil)
  (if (setq sh (cp:sheet-soft (cp:asm-name)))
    (progn
      (setq vals (cp:sheet-values sh "B4:B12"))
      (foreach p (mapcar 'cons '("L1" "L2" "L3" "N" "PE") (mapcar 'car vals))
        (if (and (cdr p) (/= (cp:s (cdr p)) "")) (setq colors (append colors (list (cons (car p) (cp:s (cdr p))))))))
      (if colors (setq cp:asm (cons (cons 'colors colors) cp:asm)))
      (if (/= (cp:s (car (nth 5 vals))) "") (setq cp:asm (cons (cons 'brand (cp:s (car (nth 5 vals)))) cp:asm)))
      (if (numberp (car (nth 6 vals))) (setq cp:asm (cons (cons 'reserve (float (car (nth 6 vals)))) cp:asm)))
      (if (numberp (car (nth 7 vals))) (setq cp:asm (cons (cons 'pct (float (car (nth 7 vals)))) cp:asm)))
      (if (and (numberp (car (nth 8 vals))) (> (car (nth 8 vals)) 0)) (setq cp:asm (cons (cons 'round (float (car (nth 8 vals)))) cp:asm)))
      (foreach r (cp:sheet-values sh "D5:E30")
        (if (and (numberp (car r)) (numberp (cadr r))) (setq rule (append rule (list (cons (float (car r)) (float (cadr r))))))))
      (if rule (setq cp:asm (cons (cons 'rule (vl-sort rule '(lambda (a b) (< (car a) (car b))))) cp:asm)))
      (cp:rel sh)))
  cp:asm)
(defun cp:put-values (sh addr rows ncol / sa i j v rg)
  (if rows
    (progn
      (setq sa (vlax-make-safearray vlax-vbVariant (cons 1 (length rows)) (cons 1 ncol)) i 1)
      (foreach r rows
        (setq j 1)
        (repeat ncol
          (setq v (nth (1- j) r))
          (vlax-safearray-put-element sa i j (cond ((null v) "") ((numberp v) v) (t (cp:s v))))
          (setq j (1+ j)))
        (setq i (1+ i)))
      (setq rg (vlax-get-property sh 'Range addr))
      (vlax-put-property rg 'Value2 (vlax-make-variant sa))
      (cp:rel rg))))
(defun cp:asm-init (sh / rg)
  (cp:put-values sh "A1:A1" (list (list (cp:ru '(1057 1041 1054 1056 1050 1040 32 1065 1048 1058 1040 32 8212 32 1089 1095 1080 1090 1072 1077 1090 32 67 80 68 82 65 87 32 40 65 117 116 111 67 65 68 41 46 32 1053 1072 1089 1090 1088 1086 1081 1082 1080 32 8212 32 1089 1090 1086 1083 1073 1094 1099 32 66 32 1080 32 68 58 69 46 32 171 1050 1072 1090 1072 1083 1086 1075 187 44 32 1089 1090 1086 1083 1073 1077 1094 32 78 44 32 1073 1077 1088 1105 1090 32 1082 1086 1083 1080 1095 1077 1089 1090 1074 1086 32 1087 1086 32 1085 1072 1080 1084 1077 1085 1086 1074 1072 1085 1080 1102 32 40 1089 1090 1086 1083 1073 1077 1094 32 67 41 46)))) 1)
  (cp:put-values sh "A3:B12"
    (list (list (cp:ru '(1053 1040 1057 1058 1056 1054 1049 1050 1048)) "")
          (list (cp:ru '(1062 1074 1077 1090 32 76 49)) (cp:ru '(1073 1077 1083 1099 1081))) (list (cp:ru '(1062 1074 1077 1090 32 76 50)) (cp:ru '(1095 1077 1088 1085 1099 1081))) (list (cp:ru '(1062 1074 1077 1090 32 76 51)) (cp:ru '(1082 1088 1072 1089 1085 1099 1081)))
          (list (cp:ru '(1062 1074 1077 1090 32 78)) (cp:ru '(1089 1080 1085 1080 1081))) (list (cp:ru '(1062 1074 1077 1090 32 80 69)) (cp:ru '(1046 47 1047))) (list (cp:ru '(1052 1072 1088 1082 1072 32 1087 1088 1086 1074 1086 1076 1072)) (cp:ru '(1055 1091 1043 1042)))
          (list (cp:ru '(1047 1072 1087 1072 1089 32 1085 1072 32 1087 1086 1076 1082 1083 1102 1095 1077 1085 1080 1077 32 40 1085 1072 32 1087 1088 1086 1074 1086 1076 41 44 32 1084 1084)) 150) (list (cp:ru '(1047 1072 1087 1072 1089 32 1076 1083 1080 1085 1099 44 32 37)) 10) (list (cp:ru '(1054 1082 1088 1091 1075 1083 1103 1090 1100 32 1076 1086 44 32 1084)) 1)) 2)
  (cp:put-values sh "D3:E16"
    (list (list (cp:ru '(1057 1045 1063 1045 1053 1048 1045 32 1055 1054 32 1058 1054 1050 1059 32 1040 1055 1055 1040 1056 1040 1058 1040)) "") (list (cp:ru '(73 110 32 1076 1086 44 32 1040)) (cp:ru '(1057 1077 1095 1077 1085 1080 1077 44 32 1082 1074 46 32 1084 1084)))
          '(10 1.5) '(16 2.5) '(25 4) '(32 6) '(40 10) '(63 16) '(80 25) '(100 35) '(125 50) '(160 70) '(200 95) '(250 120)) 2)
  (cp:put-values sh "G3:G8"
    (list (list (cp:ru '(1050 1040 1050 32 1057 1063 1048 1058 1040 1045 1058 1057 1071)))
          (list (cp:ru '(1040 1087 1087 1072 1088 1072 1090 1099 32 49 80 32 1080 32 49 80 43 78 32 1089 1090 1086 1103 1090 32 1087 1086 32 1092 1072 1079 1072 1084 32 76 49 45 76 50 45 76 51 32 1087 1086 1076 1088 1103 1076 44 32 1087 1080 1090 1072 1085 1080 1077 32 8212 32 1075 1088 1077 1073 1105 1085 1082 1086 1081 59 32 1092 1072 1079 1072 32 8212 32 1080 1079 32 171 1054 1076 1085 1086 1083 1080 1085 1077 1081 1082 1080 187 44 32 1089 1090 1086 1083 1073 1077 1094 32 86 46)))
          (list (cp:ru '(1055 1088 1086 1074 1086 1076 58 32 1082 1088 1086 1089 1089 45 1084 1086 1076 1091 1083 1100 32 45 62 32 1075 1088 1077 1073 1105 1085 1082 1072 32 47 32 1072 1087 1087 1072 1088 1072 1090 32 45 62 32 1072 1087 1087 1072 1088 1072 1090 1099 32 1075 1088 1091 1087 1087 1099 32 45 62 32 1082 1083 1077 1084 1084 1099 32 76 44 32 78 44 32 80 69 46)))
          (list (cp:ru '(1057 1077 1095 1077 1085 1080 1077 32 8212 32 1087 1086 32 1085 1086 1084 1080 1085 1072 1083 1091 32 1072 1087 1087 1072 1088 1072 1090 1072 32 40 1090 1072 1073 1083 1080 1094 1072 32 68 58 69 41 46 32 1044 1083 1080 1085 1072 32 8212 32 1087 1086 32 1095 1077 1088 1090 1077 1078 1091 32 43 32 1079 1072 1087 1072 1089 32 1085 1072 32 1087 1086 1076 1082 1083 1102 1095 1077 1085 1080 1077 32 43 32 1079 1072 1087 1072 1089 32 1076 1083 1080 1085 1099 46)))
          (list (cp:ru '(1062 1074 1077 1090 1072 32 1080 32 1084 1072 1088 1082 1091 32 1087 1088 1086 1074 1086 1076 1072 32 1087 1080 1096 1080 1090 1077 32 1082 1072 1082 32 1074 32 171 1050 1072 1090 1072 1083 1086 1075 1077 187 44 32 1089 1090 1086 1083 1073 1077 1094 32 71 58 32 1087 1086 32 1085 1080 1084 32 1080 1097 1077 1090 1089 1103 32 1089 1090 1088 1086 1082 1072 46)))
          (list (cp:ru '(1057 1090 1088 1086 1082 1080 32 1097 1080 1090 1072 32 1087 1077 1088 1077 1079 1072 1087 1080 1089 1099 1074 1072 1102 1090 1089 1103 32 1087 1088 1080 32 1082 1072 1078 1076 1086 1084 32 67 80 68 82 65 87 32 47 32 67 80 85 80 68 65 84 69 46)))) 1)
  (cp:put-values sh "A19:A19" (list (list (cp:ru '(1048 1058 1054 1043 1054 32 1044 1051 1071 32 1057 1055 1045 1062 1048 1060 1048 1050 1040 1062 1048 1048)))) 1)
  (cp:put-values sh "A20:G20" (list (list (cp:ru '(1065 1080 1090)) (cp:ru '(1042 1080 1076)) (cp:ru '(1053 1072 1080 1084 1077 1085 1086 1074 1072 1085 1080 1077 32 40 1082 1072 1082 32 1074 32 171 1050 1072 1090 1072 1083 1086 1075 1077 187 44 32 71 41)) (cp:ru '(1052 1086 1076 1077 1083 1100)) (cp:ru '(1050 1086 1083 45 1074 1086)) (cp:ru '(1045 1076 46)) (cp:ru '(1045 1089 1090 1100 32 1074 32 171 1050 1072 1090 1072 1083 1086 1075 1077 187)))) 7)
  (cp:put-values sh "J19:J19" (list (list (cp:ru '(1055 1056 1054 1042 1054 1044 1040 32 1044 1051 1071 32 1057 1041 1054 1056 1050 1048)))) 1)
  (cp:put-values sh "J20:Q20" (list (list (cp:ru '(1065 1080 1090)) (cp:ru (quote (8470))) (cp:ru '(1054 1090 1082 1091 1076 1072)) (cp:ru '(1050 1091 1076 1072)) (cp:ru '(1055 1088 1086 1074 1086 1076 1085 1080 1082)) (cp:ru '(1062 1074 1077 1090)) (cp:ru '(1057 1077 1095 1077 1085 1080 1077 44 32 1082 1074 46 32 1084 1084)) (cp:ru '(1044 1083 1080 1085 1072 44 32 1084 1084)))) 8)
  (foreach a '("A3" "D3" "G3" "A19" "J19" "A20:G20" "J20:Q20")
    (setq rg (vlax-get-property sh 'Range a))
    (vlax-put-property (vlax-get-property rg 'Font) 'Bold :vlax-true) (cp:rel rg))
  (foreach p '(("A:A" . 34) ("B:B" . 12) ("C:C" . 52) ("D:D" . 14) ("E:E" . 8) ("G:G" . 16) ("L:M" . 10))
    (setq rg (vlax-get-property sh 'Range (car p)))
    (vlax-put-property rg 'ColumnWidth (cdr p)) (cp:rel rg)))
(defun cp:asm-sheet ( / sh shs n last)
  (if (null (setq sh (cp:sheet-soft (cp:asm-name))))
    (progn
      (setq shs (vlax-get-property cp:wb 'Worksheets) n (vlax-get-property shs 'Count) last (vlax-get-property shs 'Item n))
      (setq sh (vlax-invoke-method shs 'Add))
      ;; Только аргумент Before: новый перед последним, затем последний перед новым.
      (vlax-invoke-method sh 'Move last)
      (vl-catch-all-apply 'vlax-invoke-method (list last 'Move sh))
      (vlax-put-property sh 'Name (cp:asm-name))
      (cp:asm-init sh)
      (cp:rel last) (cp:rel shs)))
  sh)
(defun cp:keep-other (rows panel)
  (vl-remove-if '(lambda (r) (or (null (car r)) (= (cp:s (car r)) "") (= (cp:s (car r)) panel))) rows))
(defun cp:write-asm ( / sh panel old new n rg path ro i)
  (setq path (cp:g 'path) panel (cp:g 'panel))
  (cp:open-book path nil)
  (setq ro (= (vlax-get-property cp:wb 'ReadOnly) :vlax-true))
  (if ro (progn (cp:close-book) (alert (cp:ru '(1050 1085 1080 1075 1072 32 1086 1090 1082 1088 1099 1090 1072 32 1090 1086 1083 1100 1082 1086 32 1076 1083 1103 32 1095 1090 1077 1085 1080 1103 32 40 1077 1105 32 1086 1090 1082 1088 1099 1083 32 1076 1088 1091 1075 1086 1081 32 1087 1086 1083 1100 1079 1086 1074 1072 1090 1077 1083 1100 32 1080 1083 1080 32 1092 1072 1081 1083 32 1090 1086 1083 1100 1082 1086 32 1076 1083 1103 32 1095 1090 1077 1085 1080 1103 41 46 32 1047 1072 1082 1088 1086 1081 1090 1077 32 1082 1085 1080 1075 1091 32 1091 32 1076 1088 1091 1075 1080 1093 32 1080 32 1087 1086 1074 1090 1086 1088 1080 1090 1077 32 67 80 85 80 68 65 84 69 46))))
    (progn
      (setq sh (cp:asm-sheet))
      ;; Итог.
      (setq old (cp:keep-other (cp:sheet-values sh "A21:G5000") panel)
            new (append old (mapcar '(lambda (r) (cons panel r)) cp:bomrows)))
      (setq rg (vlax-get-property sh 'Range "A21:G5000")) (vlax-invoke-method rg 'ClearContents) (cp:rel rg)
      (cp:put-values sh (strcat "A21:G" (itoa (+ 20 (max 1 (length new))))) new 7)
      ;; Провода.
      (setq old (cp:keep-other (cp:sheet-values sh "J21:Q5000") panel) i 0
            new (append old (mapcar '(lambda (w) (setq i (1+ i)) (list panel i (car w) (cadr w) (caddr w) (nth 3 w) (nth 4 w) (fix (+ (nth 5 w) 0.5)))) cp:wirelist)))
      (setq rg (vlax-get-property sh 'Range "J21:Q5000")) (vlax-invoke-method rg 'ClearContents) (cp:rel rg)
      (cp:put-values sh (strcat "J21:Q" (itoa (+ 20 (max 1 (length new))))) new 8)
      (cp:rel sh)
      (if cp:opened
        (progn (vlax-invoke-method cp:wb 'Save) (princ (strcat (cp:ru '(10 1057 1073 1086 1088 1082 1072 32 1097 1080 1090 1072 32 1079 1072 1087 1080 1089 1072 1085 1072 58 32 1083 1080 1089 1090 32 171 1057 1073 1086 1088 1082 1072 95 1097 1080 1090 1072 187 44 32)) path)))
        (alert (cp:ru '(1057 1073 1086 1088 1082 1072 32 1097 1080 1090 1072 32 1079 1072 1087 1080 1089 1072 1085 1072 32 1074 32 1086 1090 1082 1088 1099 1090 1091 1102 32 1082 1085 1080 1075 1091 32 69 120 99 101 108 46 32 1057 1086 1093 1088 1072 1085 1080 1090 1077 32 1082 1085 1080 1075 1091 46))))
      (cp:close-book))))
;;; Контур корпуса: центр — середина реек.
(defun cp:case-box (side / sw sh cx cy)
  (if cp:case
    (progn
      (setq sw (nth 5 cp:case) sh (nth 6 cp:case) cx (/ cp:railw 2.0) cy (/ (+ (cp:yc 0) (cp:yc (1- cp:totalrows))) 2.0))
      (cond ((= side 'left) (- cx (/ sw 2.0))) ((= side 'right) (+ cx (/ sw 2.0)))
            ((= side 'top) (+ cy (/ sh 2.0))) (t (- cy (/ sh 2.0)))))
    (cond ((= side 'left) 0.0) ((= side 'right) (cp:g 'w)) ((= side 'top) (cp:g 'h)) (t 0.0))))
(defun cp:draw-rails ( / r duct gap y1 y2 ytop ybot)
  (setq r 0)
  (repeat cp:totalrows
    (cp:rect -5.0 (- (cp:yc r) 17.5) (+ cp:railw 5.0) (+ (cp:yc r) 17.5) "CP_RAIL")
    (setq r (1+ r)))
  (if cp:case
    (progn
      (cp:rect (cp:case-box 'left) (cp:case-box 'bottom) (cp:case-box 'right) (cp:case-box 'top) "CP_CASE")
      (setq duct (nth 12 cp:case))
      (if (and duct (> duct 0) (/= (nth 3 cp:case) "MOD"))
        (progn
          (setq ytop (+ (cp:yc 0) (/ cp:maxh 2.0)) ybot (- (cp:yc (1- cp:totalrows)) (/ cp:maxh 2.0)))
          (cp:rect (- -10.0 duct) ybot -10.0 ytop "CP_DUCT")
          (cp:rect (+ cp:railw 10.0) ybot (+ cp:railw 10.0 duct) ytop "CP_DUCT")
          (setq gap (- cp:rowpitch cp:maxh) r 0)
          (if (>= gap (+ duct 10.0))
            (repeat (1- cp:totalrows)
              (setq y1 (/ (+ (cp:yc r) (cp:yc (1+ r))) 2.0))
              (cp:rect -10.0 (- y1 (/ duct 2.0)) (+ cp:railw 10.0) (+ y1 (/ duct 2.0)) "CP_DUCT")
              (setq r (1+ r)))))))))
(defun cp:draw-combs ( / p ytop ybot)
  (foreach s cp:segs
    (if (setq p (assoc (car (nth 4 s)) cp:posmapl))
      (progn
        (setq ytop (+ (nth 2 p) (/ (nth 4 p) 2.0)) ybot (- (nth 2 p) (/ (nth 4 p) 2.0)))
        (cp:rect (+ (nth 2 s) 1.0) (- ytop 7.0) (- (nth 3 s) 1.0) (- ytop 2.0) "CP_COMB")
        (cp:text (/ (+ (nth 2 s) (nth 3 s)) 2.0) (- ybot 6.0) 2.5
                 (strcat "PIN " (cp:class-name (car s)) ", " (itoa (fix (+ (nth 5 s) 0.5))) (cp:ru '(32 1084 1086 1076 46)))
                 (- (nth 3 s) (nth 2 s)) "CP_COMB")))))
(defun cp:railpitch-default (cfg / value height gap)
  (setq value (cdr (assoc 'railpitch cfg)) height (cdr (assoc 'devh cfg)) gap (cdr (assoc 'gap cfg)))
  (if (and (numberp value) (> value 0)) value
    (+ (if (numberp height) height 90.0) (if (numberp gap) gap 60.0))))
(defun cp:label-height (key fallback / value)
  (setq value (cp:g key))
  (if (and (numberp value) (> value 0)) value fallback))
(defun cp:defaults ( / cfg last)
  (setq cfg '((nrows . 0) (slots . 24) (pitch . 18.0) (reserve . 20.0)
              (gap . 60.0) (devh . 90.0)))
  (if (setq last (vlax-ldata-get "SX_PANEL" "last")) (setq cfg last))
  (if (null (assoc 'railpitch cfg)) (setq cfg (cons (cons 'railpitch (cp:railpitch-default cfg)) cfg)))
  (if (null (assoc 'textheight cfg)) (setq cfg (cons '(textheight . 4.0) cfg)))
  (if (null (assoc 'xttextheight cfg)) (setq cfg (cons '(xttextheight . 2.0) cfg)))
  (if (null (assoc 'oneblock cfg)) (setq cfg (cons '(oneblock . T) cfg)))
  (if (null (assoc 'gap cfg)) (setq cfg (cons '(gap . 60.0) cfg)))
  ;; v2.0: новые компоновки — фазы, гребёнки, N/PE, провода, корпус, запись в Excel.
  (foreach p '((comb . T) (dense . T) (npe . T) (wiring . T) (excel . T) (rails . T) (case . "") (caseseries . "ST"))
    (if (null (assoc (car p) cfg)) (setq cfg (cons p cfg))))
  (if (null (assoc 'library cfg)) (setq cfg (cons (cons 'library (cp:default-library)) cfg)))
  (if (null (assoc 'path cfg)) (setq cfg (cons (cons 'path (getenv "SX_LastXls")) cfg)))
  (if (null (assoc 'panel cfg)) (setq cfg (cons (cons 'panel (getenv "SX_LastPanel")) cfg)))
  cfg)

(defun cp:cfg-save ( / key val good)
  (setq good T)
  (foreach key '(nrows slots pitch reserve railpitch devh textheight xttextheight)
    (setq val (cp:num (get_tile (strcase (vl-symbol-name key) T))))
    (if (or (null val)
            (cond ((= key 'reserve) (or (< val 0) (>= val 100))) ((= key 'nrows) (< val 0)) (t (<= val 0)))
            (and (member key '(nrows slots)) (not (equal val (fix val) 0.000001))))
      (setq good nil)
      (cp:put key (if (member key '(nrows slots)) (fix val) val))))
  (if good
    (progn
      (cp:put 'oneblock (= (get_tile "oneblock") "1"))
      ;; Флажки и поля v2.0: в старых окнах их нет — значение не меняется.
      (foreach key '(comb dense npe excel)
        (if (setq val (get_tile (strcase (vl-symbol-name key) T))) (progn (cp:put key (= val "1")) (if (= key 'comb) (cp:put 'wiring (= val "1"))))))
      (if (setq val (get_tile "rails")) (cp:put 'rails (= val "1")))
      (foreach key '(case caseseries)
        (if (setq val (get_tile (strcase (vl-symbol-name key) T))) (cp:put key (vl-string-trim " " val))))
      (cp:put 'library (get_tile "library")) (cp:put 'panel (nth (atoi (get_tile "panel")) cp:panels)) (done_dialog 1))
    (set_tile "status" (cp:ru '(1055 1088 1086 1074 1077 1088 1100 1090 1077 32 1088 1072 1079 1084 1077 1088 1099 32 1080 32 1094 1077 1083 1086 1077 32 1082 1086 1083 1080 1095 1077 1089 1090 1074 1086 32 1088 1077 1077 1082 47 1084 1086 1076 1091 1083 1077 1081 46 32 1056 1077 1079 1077 1088 1074 58 32 48 8211 57 57 32 37 46 32 1056 1103 1076 1086 1074 58 32 48 32 8212 32 1072 1074 1090 1086 46)))))
(defun cp:dialog ( / id res key path)
  (cp:put 'railpitch (cp:railpitch-default cp:cfg))
  (cp:put 'textheight (cp:label-height 'textheight 4.0))
  (cp:put 'xttextheight (cp:label-height 'xttextheight 2.0))
  (if (null (setq path (cp:dcl-file))) (exit))
  (if (or (null (cp:g 'library)) (= (cp:g 'library) "") (not (findfile (cp:g 'library))))
    (cp:put 'library (cp:default-library)))
  (setq id (load_dialog path) res 2)
  (if (< id 0) (cp:fail (strcat (cp:ru '(1053 1077 32 1091 1076 1072 1083 1086 1089 1100 32 1079 1072 1075 1088 1091 1079 1080 1090 1100 32 1092 1072 1081 1083 32 1086 1082 1085 1072 58 32)) path)))
  (while (= res 2)
    (if (not (new_dialog "cp_main" id)) (cp:fail (cp:ru '(1053 1077 32 1091 1076 1072 1083 1086 1089 1100 32 1086 1090 1082 1088 1099 1090 1100 32 1086 1082 1085 1086 32 1082 1086 1084 1087 1086 1085 1086 1074 1082 1080 46))))
    (set_tile "file" (cp:s (cp:g 'path)))
    (set_tile "library" (cp:s (cp:g 'library)))
    (start_list "panel") (mapcar 'add_list cp:panels) (end_list)
    (set_tile "panel" (itoa (if (member (cp:g 'panel) cp:panels) (vl-position (cp:g 'panel) cp:panels) 0)))
    (foreach key '(nrows slots pitch reserve railpitch devh textheight xttextheight)
      (set_tile (strcase (vl-symbol-name key) T) (cp:s (cp:g key))))
    (set_tile "oneblock" (if (if (assoc 'oneblock cp:cfg) (cp:g 'oneblock) T) "1" "0"))
    (foreach key '(comb dense npe excel rails)
      (set_tile (strcase (vl-symbol-name key) T) (if (cp:g key) "1" "0")))
    (foreach key '(case caseseries)
      (set_tile (strcase (vl-symbol-name key) T) (cp:s (cp:g key))))
    (action_tile "browse" "(done_dialog 2)")
    (action_tile "accept" "(cp:cfg-save)") (action_tile "cancel" "(done_dialog 0)")
    (setq res (start_dialog))
    (if (= res 2)
      (if (setq path (getfiled (cp:ru '(69 120 99 101 108 32 1089 32 1086 1076 1085 1086 1083 1080 1085 1077 1081 1082 1086 1081)) (cp:g 'path) "xlsx;xlsm;xls" 0))
        (progn (cp:put 'path path) (cp:read-book path)))))
  (unload_dialog id)
  (= res 1))
(defun cp:size-fill ( / item size name)
  (setq item (nth cp:size-i cp:size-items) size (cdr (assoc (car item) cp:size-data)) name (car size))
  (set_tile "model" (cadr item))
  (set_tile "block" (itoa (if (member name cp:blocknames) (vl-position name cp:blocknames) 0)))
  (set_tile "scale" (cp:s (if (cadr size) (cadr size) 1.0)))
  (set_tile "rotation" (cp:s (if (caddr size) (caddr size) 0.0)))
  (cp:state-list (if name name "") (nth 3 size)))
(defun cp:size-store ( / key name scale rot size state)
  (setq key (car (nth cp:size-i cp:size-items)) name (nth (atoi (get_tile "block")) cp:blocknames)
        scale (cp:num (get_tile "scale")) rot (cp:num (get_tile "rotation")))
  (if (and name (/= name "") scale (> scale 0) rot)
    (progn
      (setq state (nth (atoi (get_tile "state")) cp:state-options) size (cons key (list name scale rot state)))
      (setq cp:size-data (if (assoc key cp:size-data) (subst size (assoc key cp:size-data) cp:size-data) (cons size cp:size-data))) T)
    (progn (set_tile "status" (cp:ru '(1042 1099 1073 1077 1088 1080 1090 1077 32 1074 1072 1096 32 1073 1083 1086 1082 44 32 1087 1086 1083 1086 1078 1080 1090 1077 1083 1100 1085 1099 1081 32 1084 1072 1089 1096 1090 1072 1073 32 1080 32 1091 1075 1086 1083 32 1087 1086 1074 1086 1088 1086 1090 1072 46))) nil)))
(defun cp:size-select (new)
  (if (cp:size-store) (progn (setq cp:size-i (atoi new)) (cp:size-fill))
    (set_tile "items" (itoa cp:size-i))))
(defun cp:size-accept ()
  (if (cp:size-store)
    (if (vl-some '(lambda (p) (or (null (cadr p)) (= (cadr p) ""))) cp:size-data)
      (set_tile "status" (cp:ru '(1053 1072 1079 1085 1072 1095 1100 1090 1077 32 1074 1072 1096 32 1073 1083 1086 1082 32 1082 1072 1078 1076 1086 1081 32 1087 1086 1079 1080 1094 1080 1080 46 32 1055 1091 1089 1090 1099 1077 32 1087 1086 1079 1080 1094 1080 1080 32 1086 1090 1084 1077 1095 1077 1085 1099 32 1079 1085 1072 1082 1086 1084 32 63 46)) )
      (done_dialog 1))))
(defun cp:sizes-dialog ( / id res key d size name label path)
  (setq cp:size-items nil cp:size-data nil cp:size-i 0)
  (foreach d cp:devices
    (setq key (nth 1 d) size (cdr (assoc key (cp:g 'sizes))))
    (if (null size) (setq size (list (cp:default-block d) 1.0 0.0)))
    (if (not (assoc key cp:size-items))
      (progn
        (setq label (strcat (if (car size) "" "? ") (car d) (cp:ru '(32 8212 32)) (nth 2 d)))
        (setq cp:size-items (append cp:size-items (list (list key label))))
        (setq cp:size-data (cons (cons key size) cp:size-data)))))
  (foreach d cp:terminals
    (setq key (nth 1 d) size (cdr (assoc key (cp:g 'sizes))))
    (if (null size) (setq size (list (nth 2 d) 1.0 0.0)))
    (if (not (assoc key cp:size-items))
      (setq cp:size-items (append cp:size-items (list (list key (strcat (cp:ru '(1050 1083 1077 1084 1084 1099 58 32)) (nth 2 d)))))
            cp:size-data (cons (cons key size) cp:size-data))))
  (if (null (setq path (cp:dcl-file))) (exit))
  (setq id (load_dialog path))
  (if (< id 0) (cp:fail (strcat (cp:ru '(1053 1077 32 1091 1076 1072 1083 1086 1089 1100 32 1079 1072 1075 1088 1091 1079 1080 1090 1100 32 1092 1072 1081 1083 32 1086 1082 1085 1072 58 32)) path)))
  (if (not (new_dialog "cp_sizes" id)) (cp:fail (cp:ru '(1053 1077 32 1091 1076 1072 1083 1086 1089 1100 32 1086 1090 1082 1088 1099 1090 1100 32 1086 1082 1085 1086 32 1074 1099 1073 1086 1088 1072 32 1073 1083 1086 1082 1086 1074 46))))
  (start_list "items") (mapcar '(lambda (p) (add_list (cadr p))) cp:size-items) (end_list)
  (start_list "block") (mapcar 'add_list cp:blocknames) (end_list)
  (set_tile "items" "0") (cp:size-fill)
  (action_tile "items" "(cp:size-select $value)")
  (action_tile "block" "(cp:block-choice $value)")
  (action_tile "apply" "(cp:size-store)")
  (action_tile "accept" "(cp:size-accept)") (action_tile "cancel" "(done_dialog 0)")
  (setq res (start_dialog)) (unload_dialog id)
  (if (= res 1) (progn (cp:put 'sizes cp:size-data) (cp:apply-sizes) T)))


;;; Импортируются именно пользовательские определения блоков, без их перерисовки.
(defun cp:default-library ( / base file)
  (setq base (cond ((findfile "SX_Panel.lsp"))
                   ((and (getenv "CP_DclFile")
                         (setq file (findfile (getenv "CP_DclFile")))) file)))
  ;; AND в AutoLISP возвращает T. Путь возвращаем отдельным выражением.
  ;; База рядом (2_AutoCAD/Блоки), иначе Google Диск.
  (cond ((and base (setq file (findfile (strcat (vl-filename-directory base) (cp:ru '(47 46 46 47 1041 1083 1086 1082 1080 47 83 88 95 1050 1086 1084 1087 1086 1085 1086 1074 1082 1072 95 1087 1086 1083 1100 1079 1086 1074 1072 1090 1077 1083 1100 1089 1082 1080 1077 46 100 119 103)))))) file)
        ((findfile (cp:ru '(71 58 47 1052 1086 1081 32 1076 1080 1089 1082 47 1054 1076 1085 1086 1083 1080 1085 1077 1081 1082 1072 95 1073 1072 1079 1099 47 83 88 95 1050 1086 1084 1087 1086 1085 1086 1074 1082 1072 95 1087 1086 1083 1100 1079 1086 1074 1072 1090 1077 1083 1100 1089 1082 1080 1077 46 100 119 103))))))

(defun cp:lib-close ()
  (if cp:libdbx (cp:rel cp:libdbx))
  (setq cp:libdbx nil cp:libsrc nil cp:libpath nil))
(defun cp:import-library ( / path b dest)
  ;; Здесь читаем имена, определения копируются только по запросу cp:ensure-block.
  (setq path (cp:g 'library) dest (vla-get-blocks cp:doc))
  (if (and path (/= path "") (findfile path))
    (progn
      (if (not (equal cp:libpath path))
        (progn
          (cp:lib-close)
          (vlax-for d (vla-get-documents (vlax-get-acad-object))
            (if (= (strcase (vla-get-fullname d)) (strcase path)) (setq cp:libsrc d)))
          (if (null cp:libsrc)
            (progn
              (setq cp:libdbx (vla-getinterfaceobject (vlax-get-acad-object) (strcat "ObjectDBX.AxDbDocument." (substr (getvar "ACADVER") 1 2))))
              (vla-open cp:libdbx path) (setq cp:libsrc cp:libdbx)))
          (setq cp:libpath path)))))
  (setq cp:blocknames (list "") cp:casenames nil)
  (if cp:libsrc
    (vlax-for b (vla-get-blocks cp:libsrc)
      (if (and (= (vla-get-isxref b) :vlax-false) (= (vla-get-islayout b) :vlax-false)
               (not (wcmatch (vla-get-name b) "`**,CP_*,*_G###,DKC_*,R5*,DIN_*,SX_DYN_CQEN*,SX_DYN_PLASTRON*,SX_DYN_DIN*")))
        (setq cp:blocknames (cons (vla-get-name b) cp:blocknames)))))
  (vlax-for b dest
    (if (and (not (wcmatch (vla-get-name b) "`**,CP_*,*_G###,DKC_*,R5*,DIN_*,SX_DYN_CQEN*,SX_DYN_PLASTRON*,SX_DYN_DIN*"))
             (= (vla-get-isxref b) :vlax-false) (= (vla-get-islayout b) :vlax-false)
             (not (member (vla-get-name b) cp:blocknames)))
      (setq cp:blocknames (cons (vla-get-name b) cp:blocknames))))
  (setq cp:blocknames (vl-sort cp:blocknames '<))
  cp:blocknames)

(defun cp:ensure-block (name / b arr result)
  (if (not (tblsearch "BLOCK" name))
    (progn
      (if (null cp:libsrc) (cp:fail (strcat (cp:ru '(1053 1077 1090 32 1073 1083 1086 1082 1072 32 1074 32 1095 1077 1088 1090 1077 1078 1077 32 1080 32 1085 1077 32 1086 1090 1082 1088 1099 1090 1072 32 1073 1080 1073 1083 1080 1086 1090 1077 1082 1072 58 32)) name)))
      (setq b (vl-catch-all-apply 'vla-item (list (vla-get-blocks cp:libsrc) name)))
      (if (vl-catch-all-error-p b) (cp:fail (strcat (cp:ru '(1042 32 1073 1080 1073 1083 1080 1086 1090 1077 1082 1077 32 1085 1077 1090 32 1073 1083 1086 1082 1072 58 32)) name)))
      (setq arr (vlax-make-safearray vlax-vbObject '(0 . 0))) (vlax-safearray-fill arr (list b))
      (setq result (vl-catch-all-apply 'vla-copyobjects (list cp:libsrc arr (vla-get-blocks cp:doc))))
      (if (vl-catch-all-error-p result) (cp:fail (vl-catch-all-error-message result))))))
(defun cp:set-state (ob state / prop allowed found)
  (if (and state (/= state "") (= (vla-get-isdynamicblock ob) :vlax-true))
    (progn
      (foreach prop (vlax-invoke ob 'GetDynamicBlockProperties)
        (setq allowed (cp:dyn-values prop))
        (if (member state allowed)
          (progn (vla-put-value prop (vlax-make-variant state (vlax-variant-type (vla-get-value prop)))) (setq found T))))
      (if (null found) (cp:fail (strcat (cp:ru '(1053 1077 1090 32 1080 1089 1087 1086 1083 1085 1077 1085 1080 1103 32 1076 1080 1085 1072 1084 1080 1095 1077 1089 1082 1086 1075 1086 32 1073 1083 1086 1082 1072 58 32)) state)))))
  (vla-update ob))
(defun cp:dyn-values (prop / vals)
  (setq vals (vl-catch-all-apply
    '(lambda ()
       (setq vals (cp:v (vla-get-allowedvalues prop)))
       (if (= (type vals) 'SAFEARRAY)
         (vl-remove-if-not '(lambda (v) (= (type v) 'STR)) (mapcar 'cp:v (vlax-safearray->list vals))))) nil))
  (if (not (vl-catch-all-error-p vals)) vals))
(defun cp:states (name / tmp ob result prop)
  (cp:ensure-block name)
  (setq tmp (vla-add (vla-get-blocks cp:doc) (cp:p 0.0 0.0) (strcat "CP_STATES_" (itoa (abs (getvar "MILLISECS"))))))
  (setq ob (vla-insertblock tmp (cp:p 0.0 0.0) name 1.0 1.0 1.0 0.0))
  (if (= (vla-get-isdynamicblock ob) :vlax-true)
    (foreach prop (vlax-invoke ob 'GetDynamicBlockProperties) (setq result (append result (cp:dyn-values prop)))))
  (vla-delete ob) (vla-delete tmp)
  (cons "" result))
(defun cp:state-list (name state)
  (setq cp:state-options (if (/= name "") (cp:states name) (list "")))
  (start_list "state") (mapcar 'add_list cp:state-options) (end_list)
  (set_tile "state" (itoa (if (member state cp:state-options) (vl-position state cp:state-options) 0))))
(defun cp:block-choice (index)
  (cp:state-list (nth (atoi index) cp:blocknames) ""))


(defun cp:default-block (d / parts name row cat q)
  (setq name (nth 2 d))
  (if (and (member (nth 5 d) '("QF" "QS")) (numberp (nth 6 d)) (>= (nth 6 d) 3)
           (< (- (nth 6 d) 3) (length cp:rows)))
    (setq row (nth (- (nth 6 d) 3) cp:rows)))
  (setq parts (cp:qparts (if (and row (cp:at row 8)) (cp:at row 8) name))
        cat (cp:model-catalog name) q (if cat (cp:s (nth 16 cat)) ""))
  (cond
    ;; «Каталог», столбец Q «Блок компоновки» — главнее подбора.
    ((and (/= q "") (member q cp:blocknames)) q)
    ((and (= (nth 5 d) "QF") (caddr parts) (= (car parts) "2P")) "DA_1PN_36")
    ((member name cp:blocknames) name)
    ((member (strcat name "_FRONT") cp:blocknames) (strcat name "_FRONT"))
    ((= (nth 5 d) "QS")
     (cond ((= (car parts) "1P") "AV_1P_18") ((= (car parts) "2P") "AV_2P_36") ((= (car parts) "4P") "AV_4P_72") (t "AV_3P_54")))
    ((= (nth 5 d) "QF")
     (cond ((and (caddr parts) (member (car parts) '("3P" "4P"))) "DA_4P_135")
           ((= (car parts) "1P") "AV_1P_18") ((= (car parts) "2P") "AV_2P_36")
           ((= (car parts) "3P") "AV_3P_54") ((= (car parts) "4P") "AV_4P_72")))
    ((= (nth 5 d) "KM") "CT_ACDC_4P_63A_FRONT")
    ((= (nth 5 d) "PS") (if (member "ARV-DRP480-PFC-24" cp:blocknames) "ARV-DRP480-PFC-24" nil))))
(defun cp:measure (name scale rot state / key cached blocks tmp ob p1 p2 result)
  (setq key (list name scale rot state))
  (if (setq cached (assoc key cp:measure-cache)) (cdr cached)
    (progn
      (cp:ensure-block name)
      (setq blocks (vla-get-blocks cp:doc) tmp (vla-add blocks (cp:p 0.0 0.0) (strcat "CP_MEASURE_" (itoa (abs (getvar "MILLISECS"))))))
      (setq ob (vla-insertblock tmp (cp:p 0.0 0.0) name scale scale scale (* pi (/ rot 180.0))))
      (cp:set-state ob state)
      (vla-getboundingbox ob 'p1 'p2)
      (setq p1 (vlax-safearray->list p1) p2 (vlax-safearray->list p2) result (list (car p1) (cadr p1) (car p2) (cadr p2)))
      (vla-delete ob) (vla-delete tmp)
      (if (or (< (- (nth 2 result) (nth 0 result)) 0.01) (< (- (nth 3 result) (nth 1 result)) 0.01)) (cp:fail (strcat (cp:ru '(1053 1077 1074 1077 1088 1085 1099 1077 32 1075 1072 1073 1072 1088 1080 1090 1099 32 1073 1083 1086 1082 1072 58 32)) name)))
      (setq cp:measure-cache (cons (cons key result) cp:measure-cache)) result)))
(defun cp:mapping (key) (cdr (assoc key (cp:g 'sizes))))




(defun cp:place-block (mapping x y lay id / name scale rot bb ob att)
  (setq name (car mapping) scale (cadr mapping) rot (caddr mapping) bb (cp:measure name scale rot (nth 3 mapping)))
  (setq ob (vla-insertblock cp:space (cp:p (- x (nth 0 bb)) (- y (/ (+ (nth 1 bb) (nth 3 bb)) 2.0))) name scale scale scale (* pi (/ rot 180.0))))
  (cp:set-state ob (nth 3 mapping))
  (vla-put-layer ob lay)
  (if (and id (= (vla-get-hasattributes ob) :vlax-true))
    (foreach att (vlax-invoke ob 'GetAttributes)
      (if (member (strcase (vla-get-tagstring att)) (list "ID" "QF" "XT" "TAG" "NAME" "1" (strcase (cp:ru '(1050 1052))))) (vla-put-textstring att id))))
  ob)

;;; Геометрия блока. Все точки локальные, миллиметры, масштаб 1:1.
(defun cp:p (x y) (vlax-3d-point (list x y 0.0)))
(defun cp:layer (name color / lay)
  (setq lay (vl-catch-all-apply 'vla-item (list (vla-get-layers cp:doc) name)))
  (if (vl-catch-all-error-p lay) (setq lay (vla-add (vla-get-layers cp:doc) name)))
  (vla-put-color lay color) name)
(defun cp:layers ()
  (foreach p '(("CP_DEVICES" 7) ("CP_TEXT" 7) ("CP_RAIL" 8) ("CP_CASE" 8) ("CP_DUCT" 9) ("CP_COMB" 1)) (cp:layer (car p) (cadr p))))

(defun cp:style ( / st)
  (setq st (vl-catch-all-apply 'vla-item (list (vla-get-textstyles cp:doc) "CP_GOST")))
  (if (vl-catch-all-error-p st) (setq st (vla-add (vla-get-textstyles cp:doc) "CP_GOST")))
  (vla-setfont st "GOST 2.304 type A" :vlax-false :vlax-false 204 34)
  (vla-put-height st 0.0) (vla-put-width st 1.0))
(defun cp:line (x1 y1 x2 y2 lay / ob)
  (setq ob (vla-addline cp:space (cp:p x1 y1) (cp:p x2 y2))) (vla-put-layer ob lay) ob)
(defun cp:rect (x1 y1 x2 y2 lay / ob pts)
  (setq pts (vlax-make-safearray vlax-vbDouble '(0 . 7)))
  (vlax-safearray-fill pts (list x1 y1 x2 y1 x2 y2 x1 y2))
  (setq ob (vla-addlightweightpolyline cp:space pts))
  (vla-put-closed ob :vlax-true) (vla-put-layer ob lay) ob)
(defun cp:text (x y h text width lay / ob bb1 bb2 actual)
  (setq ob (vla-addtext cp:space text (cp:p x y) h))
  (vla-put-stylename ob "CP_GOST") (vla-put-layer ob lay)
  (vla-put-alignment ob 10) (vla-put-textalignmentpoint ob (cp:p x y))
  (vla-getboundingbox ob 'bb1 'bb2)
  (setq actual (- (car (vlax-safearray->list bb2)) (car (vlax-safearray->list bb1))))
  (if (and (> width 0) (> actual width)) (vla-put-scalefactor ob (/ width actual)))
  ob)
(defun cp:circle (x y r lay / ob)
  (setq ob (vla-addcircle cp:space (cp:p x y) r)) (vla-put-layer ob lay))
(defun cp:dim (x1 y1 x2 y2 xt yt / ob)
  (setq ob (vla-adddimaligned cp:space (cp:p x1 y1) (cp:p x2 y2) (cp:p xt yt)))
  (vla-put-layer ob "CP_DIMS") (vla-put-textheight ob 4.0) (vla-put-arrowheadsize ob 3.0)
  (vla-put-textstyle ob "CP_GOST") (vla-put-linearscalefactor ob 1.0)
  (vla-put-primaryunitsprecision ob 0) (vla-put-textoverride ob "<>"))
(defun cp:yc (row) (- cp:rowtop (* row cp:rowpitch)))
(defun cp:device (pos left / d x y w h ob part curve at tag rating label ph)
  (setq d (car pos) x (+ left (nth 2 pos)) y (cp:yc (cadr pos)) w (* (nth 3 d) (cp:g 'pitch)) h (nth 4 d))
  (setq ob (cp:place-block (list (nth 7 d) (nth 8 d) (nth 9 d) (nth 10 d)) x y "CP_DEVICES" (car d)))
  (if (and (member (nth 5 d) '("QF" "QS")) (= (vla-get-hasattributes ob) :vlax-true))
    (progn
      (setq rating (cp:s (cp:at (nth (- (nth 6 d) 3) cp:rows) 8)) part (cp:qparts rating) curve (cp:curve rating))
      (foreach at (vlax-invoke ob 'GetAttributes)
        (setq tag (strcase (vla-get-tagstring at)))
        (cond ((= tag "IN_A") (vla-put-textstring at (if (cadr part) (rtos (cadr part) 2 0) "")))
              ((= tag "CURVE") (vla-put-textstring at (if curve curve "")))
              ((= tag "POLES") (vla-put-textstring at (car part)))
              ((= tag "DESCRIPTION") (vla-put-textstring at (nth 2 d)))))))
  (setq label (car d))
  (if (setq ph (cp:inf (car d) 'aphase)) (setq label (strcat label " " ph (if (cp:inf (car d) 'assumed) "?" ""))))
  (cp:text (+ x (/ w 2.0)) (+ y (/ h 2.0) 8.0) (cp:label-height 'textheight 4.0) label (- w 2.0) "CP_TEXT"))
(defun cp:draw-geometry ( / w h pos d xti tr y x ob top y0 note)
  (setq w (cp:g 'w) h (cp:g 'h) top (max (+ h 22.0) (+ (cp:case-box 'top) 22.0)) y0 (min 0.0 (cp:case-box 'bottom)))
  (if (cp:g 'rails) (cp:draw-rails))
  (cp:text (/ w 2.0) top 6.0 (strcat (cp:ru '(1050 1086 1084 1087 1086 1085 1086 1074 1082 1072 32 1072 1087 1087 1072 1088 1072 1090 1086 1074 32)) (cp:g 'panel)) w "CP_TEXT")
  (if cp:case (cp:text (/ w 2.0) (- top 10.0) 3.5 (strcat (nth 1 cp:case) (cp:ru '(32 8212 32)) (nth 2 cp:case)) (max w (nth 5 cp:case)) "CP_TEXT"))
  (if cp:case-note (cp:text (/ w 2.0) (- top (if cp:case 18.0 10.0)) 3.5 cp:case-note w "CP_TEXT"))
  (foreach pos cp:positions (cp:device pos 0.0))
  (foreach pos cp:xtpositions
    (setq d (car pos) y (cp:yc (+ cp:devrows (cadr pos))) x (nth 2 pos))
    (cp:place-block (list (nth 7 d) (nth 8 d) (nth 9 d) (nth 10 d)) x y "CP_DEVICES" (car d))
    (if (/= (nth 5 d) "CAP")
      (progn
        (setq ob (cp:text (+ x (/ (nth 3 d) 2.0)) (+ y (/ (nth 4 d) 2.0) 17.0) (cp:label-height 'xttextheight 2.0) (car d) 33.0 "CP_TEXT"))
        (vla-put-rotation ob (/ pi 2.0)))))
  (if cp:segs (cp:draw-combs))
  (cp:draw-list (+ (max w (cp:case-box 'right)) 35.0) top)
  (cp:text (/ w 2.0) (- y0 22.0) 4.0
    (strcat (cp:ru '(1050 1088 1086 1089 1089 45 1084 1086 1076 1091 1083 1100 58 32 76 49 61)) (itoa (car cp:cross-counts)) "; L2=" (itoa (cadr cp:cross-counts))
            "; L3=" (itoa (caddr cp:cross-counts)) "; N=" (itoa (nth 3 cp:cross-counts)) (cp:ru '(59 32 43 32 1087 1080 1090 1072 1085 1080 1077 32 1085 1072 32 1087 1086 1083 1102 1089))
            (if (and cp:npe-counts (vl-some '(lambda (d) (= (nth 5 d) "NPE")) cp:devices))
              (strcat (cp:ru '(46 32 1052 1086 1076 1091 1083 1100 32 78 47 80 69 58 32 78 61)) (itoa (car cp:npe-counts)) "; PE=" (itoa (cadr cp:npe-counts))) ""))
    (+ w 20.0) "CP_TEXT")
  (if (and (> cp:cross-unknown 0) (not (cp:g 'comb)))
    (cp:text (/ w 2.0) (- y0 34.0) 3.5 (cp:ru '(1060 1072 1079 1099 32 1095 1072 1089 1090 1080 32 1072 1074 1090 1086 1084 1072 1090 1086 1074 32 1085 1077 32 1079 1072 1076 1072 1085 1099 58 32 1084 1077 1089 1090 1086 32 1087 1088 1077 1076 1091 1089 1084 1086 1090 1088 1077 1085 1086 32 1085 1072 32 1082 1072 1078 1076 1086 1081 32 1092 1072 1079 1077 46)) w "CP_TEXT"))
  (if (setq note (vl-remove-if-not '(lambda (d) (cp:inf (car d) 'assumed)) cp:devices))
    (cp:text (/ w 2.0) (- y0 34.0) 3.5
      (strcat (cp:ru '(1060 1072 1079 1072 32 1085 1077 32 1079 1072 1076 1072 1085 1072 32 1074 32 171 1054 1076 1085 1086 1083 1080 1085 1077 1081 1082 1077 187 32 40 1089 1090 1086 1083 1073 1077 1094 32 86 41 44 32 1087 1088 1080 1085 1103 1090 1072 32 1087 1086 32 1075 1088 1077 1073 1105 1085 1082 1077 58 32))
              (apply 'strcat (mapcar '(lambda (d) (strcat (car d) "=" (cp:inf (car d) 'aphase) " ")) note)))
      (+ w 20.0) "CP_TEXT")))

(defun cp:draw-list (x top / y d txt ob r)
  (cp:text (+ x 130.0) (+ top 10.0) 5.0 (cp:ru '(1040 1087 1087 1072 1088 1072 1090 1099 32 1097 1080 1090 1072)) 260.0 "CP_TEXT")
  (setq y (- top 10.0))
  (foreach d cp:devices
    (setq txt (strcat (car d) "   " (nth 2 d) "   [" (cp:s (nth 3 d)) " DIN]"))
    (setq ob (vla-addtext cp:space txt (cp:p x y) 4.0))
    (vla-put-layer ob "CP_TEXT") (vla-put-stylename ob "CP_GOST")
    (setq y (- y 10.0)))
  (if cp:bomrows
    (progn
      (setq y (- y 8.0))
      (cp:text (+ x 130.0) y 5.0 (cp:ru '(1057 1073 1086 1088 1082 1072 32 1097 1080 1090 1072 32 40 1074 32 69 120 99 101 108 32 8212 32 1083 1080 1089 1090 32 171 1057 1073 1086 1088 1082 1072 95 1097 1080 1090 1072 187 41)) 260.0 "CP_TEXT")
      (setq y (- y 12.0))
      (foreach r cp:bomrows
        (setq ob (vla-addtext cp:space (strcat (cadr r) (cp:ru '(32 8212 32)) (cp:s (nth 3 r)) " " (nth 4 r)) (cp:p x y) 4.0))
        (vla-put-layer ob "CP_TEXT") (vla-put-stylename ob "CP_GOST")
        (setq y (- y 8.0))))))

;;; Родительский блок и сохранённые параметры. Обновление меняет только выбранную компоновку.
(defun cp:tag (ob /)
  (regapp cp:app)
  (vla-setxdata ob
    (vlax-safearray-fill (vlax-make-safearray vlax-vbInteger '(0 . 1)) '(1001 1000))
    (vlax-safearray-fill (vlax-make-safearray vlax-vbVariant '(0 . 1)) (list cp:app (cp:g 'panel))))
  (vlax-ldata-put ob "settings" cp:cfg))
(defun cp:build (point / blocks name ob oldspace)
  (cp:layers) (cp:style)
  (setq blocks (vla-get-blocks cp:doc) name (strcat "CP_LAYOUT_" (itoa (abs (getvar "MILLISECS")))))
  (while (tblsearch "BLOCK" name) (setq name (strcat name "_")))
  (setq cp:newdef (vla-add blocks (cp:p 0.0 0.0) name) cp:space cp:newdef)
  (cp:draw-geometry)
  (setq ob (vla-insertblock (vla-get-modelspace cp:doc) (vlax-3d-point point) name 1.0 1.0 1.0 0.0))
  (setq cp:pendingnew ob)
  (vla-put-layer ob "CP_DEVICES") (cp:tag ob) ob)
(defun cp:block-frame (ob)
  (list (vlax-safearray->list (vlax-variant-value (vla-get-insertionpoint ob)))
        (vla-get-xscalefactor ob) (vla-get-yscalefactor ob) (vla-get-zscalefactor ob) (vla-get-rotation ob)))
(defun cp:part-id (entity / data)
  (if (setq data (cadr (assoc -3 (entget entity (list cp:partsapp))))) (cdr (assoc 1000 (cdr data)))))
(defun cp:part-tag (entity id)
  (regapp cp:partsapp)
  (entmod (append (entget entity) (list (list -3 (list cp:partsapp (cons 1000 id)))))))
(defun cp:part-pose (entity / data kind point factor)
  (setq data (entget entity) kind (cdr (assoc 0 data)))
  (if (member kind '("TEXT" "MTEXT" "INSERT"))
    (progn
      (setq point (if (and (= kind "TEXT") (or (/= (cdr (assoc 72 data)) 0) (/= (cdr (assoc 73 data)) 0)))
                    (cdr (assoc 11 data)) (cdr (assoc 10 data)))
            factor (cdr (assoc (if (= kind "INSERT") 41 40) data)))
      (if (and point factor (> factor 0)) (list point (if (assoc 50 data) (cdr (assoc 50 data)) 0.0) factor)))))
(defun cp:parts-entities (id record / result handle entity)
  (foreach handle (cdr (assoc 'handles record))
    (if (and (setq entity (handent handle)) (entget entity) (equal (cp:part-id entity) id)) (setq result (cons entity result))))
  (reverse result))
(defun cp:parts-frame (id record / frame anchor entity current previous delta factor vector rotated)
  (setq frame (cdr (assoc 'frame record)))
  ;; Title is normally the first anchor. Deleted members are skipped; moving the whole layout retains its frame.
  (foreach anchor (cdr (assoc 'anchors record))
    (if (and (null current) (setq entity (handent (car anchor))) (entget entity) (equal (cp:part-id entity) id)
             (setq current (cp:part-pose entity))) (setq previous (cdr anchor))))
  (if (and current previous)
    (progn
      (setq delta (- (cadr current) (cadr previous)) factor (/ (caddr current) (caddr previous))
            vector (mapcar '- (car previous) (car frame))
            rotated (list (- (* (car vector) (cos delta)) (* (cadr vector) (sin delta)))
                          (+ (* (car vector) (sin delta)) (* (cadr vector) (cos delta))) (caddr vector)))
      (list (mapcar '- (car current) (mapcar '(lambda (n) (* n factor)) rotated))
            (* (nth 1 frame) factor) (* (nth 2 frame) factor) (* (nth 3 frame) factor) (+ (nth 4 frame) delta)))
    frame))
(defun cp:parts-pick (entity / id record entities)
  (if (and (setq id (cp:part-id entity)) (setq record (vlax-ldata-get cp:partsapp id))
           (member (cdr (assoc 5 (entget entity))) (cdr (assoc 'handles record))))
    (progn
      (setq entities (cp:parts-entities id record))
      (list (list 'parts id entities) (cdr (assoc 'settings record)) (cp:parts-frame id record)))))
(defun cp:container-delete (container / entity deleted result failed)
  (if (and (= (type container) 'LIST) (= (car container) 'parts))
    (progn
      (foreach entity (caddr container)
        (if (and (not failed) (entget entity))
          (progn
            (setq result (vl-catch-all-apply 'entdel (list entity)))
            (if (or (vl-catch-all-error-p result) (null result)) (setq failed T) (setq deleted (cons entity deleted))))))
      (if failed
        (progn
          (foreach entity deleted (entdel entity))
          (cp:fail (cp:ru '(1053 1077 32 1091 1076 1072 1083 1086 1089 1100 32 1091 1076 1072 1083 1080 1090 1100 32 1082 1086 1084 1087 1086 1085 1086 1074 1082 1091 46 32 1055 1088 1086 1074 1077 1088 1100 1090 1077 32 1073 1083 1086 1082 1080 1088 1086 1074 1082 1091 32 1077 1105 32 1089 1083 1086 1105 1074 46))))
        (vlax-ldata-delete cp:partsapp (cadr container))))
    (vla-delete container)))
(defun cp:cleanup-new ( / entity)
  (foreach entity cp:pendingparts (if (entget entity) (entdel entity)))
  (if cp:pendinggroup (vlax-ldata-delete cp:partsapp cp:pendinggroup))
  (if cp:pendingnew (vl-catch-all-apply 'vla-delete (list cp:pendingnew)))
  (if cp:newdef (vl-catch-all-apply 'vla-delete (list cp:newdef)))
  (setq cp:pendingparts nil cp:pendinggroup nil cp:pendingnew nil cp:newdef nil))
(defun cp:separate (ob frame / id result entity owner before cursor handles anchors pose record)
  ;; Only the outer layout is exploded. Collect new entities directly, including non-uniformly scaled output.
  (setq entity (vlax-vla-object->ename ob) owner (cdr (assoc 330 (entget entity))) before (entlast)
        result (vl-catch-all-apply 'vla-explode (list ob)) cursor (entnext before) cp:pendingparts nil)
  (while cursor
    (if (equal owner (cdr (assoc 330 (entget cursor)))) (setq cp:pendingparts (cons cursor cp:pendingparts)))
    (setq cursor (entnext cursor)))
  (setq cp:pendingparts (reverse cp:pendingparts))
  (if (or (vl-catch-all-error-p result) (null cp:pendingparts)) (cp:fail (cp:ru '(1053 1077 32 1091 1076 1072 1083 1086 1089 1100 32 1088 1072 1079 1076 1077 1083 1080 1090 1100 32 1082 1086 1084 1087 1086 1085 1086 1074 1082 1091 46 32 1048 1089 1093 1086 1076 1085 1099 1081 32 1073 1083 1086 1082 32 1089 1086 1093 1088 1072 1085 1105 1085 46))))
  (setq id (strcat "CP_PARTS_" (itoa (abs (getvar "MILLISECS")))))
  (while (vlax-ldata-get cp:partsapp id) (setq id (strcat id "_")))
  (foreach entity cp:pendingparts
    (if (null (cp:part-tag entity id)) (cp:fail (cp:ru '(1053 1077 32 1091 1076 1072 1083 1086 1089 1100 32 1088 1072 1079 1076 1077 1083 1080 1090 1100 32 1082 1086 1084 1087 1086 1085 1086 1074 1082 1091 46 32 1048 1089 1093 1086 1076 1085 1099 1081 32 1073 1083 1086 1082 32 1089 1086 1093 1088 1072 1085 1105 1085 46))))
    (setq handles (cons (cdr (assoc 5 (entget entity))) handles))
    (if (setq pose (cp:part-pose entity)) (setq anchors (cons (cons (cdr (assoc 5 (entget entity))) pose) anchors))))
  (setq record (list (cons 'settings cp:cfg) (cons 'frame frame) (cons 'handles (reverse handles)) (cons 'anchors (reverse anchors)))
        cp:pendinggroup id)
  (vlax-ldata-put cp:partsapp id record)
  (vla-delete ob) (setq cp:pendingnew nil)
  (if cp:newdef (progn (vl-catch-all-apply 'vla-delete (list cp:newdef)) (setq cp:newdef nil)))
  (list 'parts id cp:pendingparts))
(defun cp:pick ( / ss ob cfg parts)
  (if (setq ss (entsel (cp:ru '(1042 1099 1073 1077 1088 1080 1090 1077 32 1082 1086 1084 1087 1086 1085 1086 1074 1082 1091 32 1080 1083 1080 32 1077 1105 32 1101 1083 1077 1084 1077 1085 1090 46))))
    (if (cp:part-id (car ss)) (cp:parts-pick (car ss))
      (progn
        (setq ob (vlax-ename->vla-object (car ss)))
        (if (and (= (vla-get-objectname ob) "AcDbBlockReference")
                 (assoc -3 (entget (car ss) (list cp:app))) (setq cfg (vlax-ldata-get ob "settings")))
          (list ob cfg (cp:block-frame ob))
          (progn (princ (cp:ru '(1069 1090 1086 32 1085 1077 32 1082 1086 1084 1087 1086 1085 1086 1074 1082 1072 44 32 1089 1086 1079 1076 1072 1085 1085 1072 1103 32 67 80 68 82 65 87 46))) nil))))))
(defun cp:run (update edit / *error* pick old new staged frame point undo path ready cp:failure)
  (defun *error* (msg)
    (cp:close-book) (cp:lib-close)
    (if (null new) (cp:cleanup-new))
    (if undo (vl-catch-all-apply 'vla-endundomark (list cp:doc)))
    (if (and (not cp:failure) (not (member msg '("Function cancelled" "quit / exit abort"))))
      (progn (princ (strcat "\nCPDRAW: " msg " [" (vl-princ-to-string cp:stage) "]"))
             (if (getenv "CP_Debug") (vl-catch-all-apply 'vl-bt nil))))
    (princ))
  (setq cp:stage 'start)
  (setq cp:doc (vla-get-activedocument (vlax-get-acad-object)) cp:newdef nil cp:measure-cache nil cp:pendingnew nil cp:pendingparts nil cp:pendinggroup nil
        cp:case-cache nil cp:asm nil)
  (if update
    (progn
      (if (null (setq pick (cp:pick))) (exit))
      (setq old (car pick) cp:cfg (cadr pick) frame (caddr pick) point (car frame)))
    (setq cp:cfg (cp:defaults)))
  (setq path (cp:g 'path))
  (if (or (null path) (not (findfile path))) (setq path (getfiled (cp:ru '(69 120 99 101 108 32 1089 32 1086 1076 1085 1086 1083 1080 1085 1077 1081 1082 1086 1081)) "" "xlsx;xlsm;xls" 0)))
  (if (null path) (exit))
  (cp:put 'path path) (setq cp:stage 'read-book) (cp:read-book path)
  (if (null cp:panels) (cp:fail (cp:ru '(1042 32 1086 1076 1085 1086 1083 1080 1085 1077 1081 1082 1077 32 1085 1077 1090 32 1097 1080 1090 1086 1074 46))))
  (if (and update (not edit) (not (member (cp:g 'panel) cp:panels))) (cp:fail (cp:ru '(1057 1086 1093 1088 1072 1085 1105 1085 1085 1099 1081 32 1097 1080 1090 32 1085 1077 32 1085 1072 1081 1076 1077 1085 32 1074 32 69 120 99 101 108 46 32 1048 1089 1087 1086 1083 1100 1079 1091 1081 1090 1077 32 67 80 69 68 73 84 32 1076 1083 1103 32 1074 1099 1073 1086 1088 1072 32 1076 1088 1091 1075 1086 1075 1086 32 1097 1080 1090 1072 46))))
  (setq cp:stage 'library) (cp:import-library)
  (setq cp:stage 'dialog)
  (if (and edit (not (cp:dialog))) (exit))
  (setq ready nil)
  (while (not ready)
    (cp:import-library)
    (setq cp:stage 'collect) (cp:collect (cp:g 'panel)) (setq cp:stage 'apply-sizes) (cp:apply-sizes)
    (if (or edit (vl-some '(lambda (d) (null (nth 7 d))) cp:devices))
      (progn (setq cp:stage 'sizes-dialog) (if (not (cp:sizes-dialog)) (exit))))
    (setq cp:stage 'plan)
    (if (cp:plan) (setq ready T)
      (progn (alert cp:problem) (if (not (cp:dialog)) (exit)))))
  (if (not update)
    (progn
      (setq point (getpoint (cp:ru '(1059 1082 1072 1078 1080 1090 1077 32 1090 1086 1095 1082 1091 32 1074 1089 1090 1072 1074 1082 1080 32 1082 1086 1084 1087 1086 1085 1086 1074 1082 1080 32 1072 1087 1087 1072 1088 1072 1090 1086 1074 58 32))))
      (if (null point) (exit))
      (setq point (trans point 1 0))))
  (vla-startundomark cp:doc) (setq undo T)
  (setq cp:stage 'build staged (cp:build point))
  (if frame
    (progn
      (vla-put-xscalefactor staged (nth 1 frame)) (vla-put-yscalefactor staged (nth 2 frame))
      (vla-put-zscalefactor staged (nth 3 frame)) (vla-put-rotation staged (nth 4 frame))))
  (if (and (assoc 'oneblock cp:cfg) (not (cp:g 'oneblock)))
    (setq staged (cp:separate staged (cp:block-frame staged))))
  (if old (cp:container-delete old))
  (setq new staged cp:pendingparts nil cp:pendinggroup nil cp:pendingnew nil)
  (vlax-ldata-put "SX_PANEL" "last" cp:cfg)
  (vla-endundomark cp:doc) (setq undo nil)
  (cp:lib-close) (vla-regen cp:doc 1)
  ;; Сборка в Excel — после чертежа; сбой записи чертёж не отменяет.
  (if (and (cp:g 'excel) (cp:g 'wiring))
    (if (vl-catch-all-error-p (setq ready (vl-catch-all-apply 'cp:write-asm)))
      (progn (cp:close-book) (alert (strcat (cp:ru '(1057 1073 1086 1088 1082 1072 32 1097 1080 1090 1072 32 1085 1077 32 1079 1072 1087 1080 1089 1072 1085 1072 32 1074 32 69 120 99 101 108 58 32)) (vl-catch-all-error-message ready)))))
    (princ (cp:ru '(10 1057 1073 1086 1088 1082 1072 32 1074 32 69 120 99 101 108 32 1074 1099 1082 1083 1102 1095 1077 1085 1072 32 1076 1083 1103 32 1101 1090 1086 1081 32 1082 1086 1084 1087 1086 1085 1086 1074 1082 1080 46 32 1042 1082 1083 1102 1095 1080 1090 1077 32 171 1047 1072 1087 1080 1089 1072 1090 1100 32 1074 32 69 120 99 101 108 187 32 1095 1077 1088 1077 1079 32 67 80 69 68 73 84 46))))
  (princ (strcat (cp:ru '(10 1050 1086 1084 1087 1086 1085 1086 1074 1082 1072 32 1087 1086 1089 1090 1088 1086 1077 1085 1072 58 32)) (cp:g 'panel) (cp:ru '(44 32 1072 1087 1087 1072 1088 1072 1090 1086 1074 32)) (itoa (length cp:devices)) (cp:ru '(44 32 1082 1083 1077 1084 1084 32)) (itoa (length cp:terminals)) "."))
  (princ))
(defun c:CPDRAW () (cp:run nil T))
(defun c:CPUPDATE () (cp:run T nil))
(defun c:CPEDIT () (cp:run T T))
(defun c:CPDELETE ( / pick doc)
  (if (setq pick (cp:pick))
    (progn (setq doc (vla-get-activedocument (vlax-get-acad-object)))
      (vla-startundomark doc) (cp:container-delete (car pick)) (vla-endundomark doc))) (princ))
(defun c:CPEXPLODE ( / *error* pick source result undo cp:failure)
  (defun *error* (msg)
    (if (null result) (cp:cleanup-new))
    (if undo (vl-catch-all-apply 'vla-endundomark (list cp:doc)))
    (if (and (not cp:failure) (not (member msg '("Function cancelled" "quit / exit abort")))) (princ (strcat "\nCPDRAW: " msg)))
    (princ))
  (setq cp:newdef nil cp:pendingnew nil cp:pendingparts nil cp:pendinggroup nil)
  (if (setq pick (cp:pick))
    (if (= (type (setq source (car pick))) 'LIST)
      (princ (cp:ru '(1050 1086 1084 1087 1086 1085 1086 1074 1082 1072 32 1091 1078 1077 32 1089 1086 1089 1090 1086 1080 1090 32 1080 1079 32 1086 1090 1076 1077 1083 1100 1085 1099 1093 32 1086 1073 1098 1077 1082 1090 1086 1074 46)))
      (progn
        (setq cp:doc (vla-get-activedocument (vlax-get-acad-object)) cp:cfg (cadr pick))
        (cp:put 'oneblock nil)
        (vla-startundomark cp:doc) (setq undo T)
        (setq result (cp:separate source (caddr pick)) cp:pendingparts nil cp:pendinggroup nil)
        (vlax-ldata-put "SX_PANEL" "last" cp:cfg)
        (vla-endundomark cp:doc) (setq undo nil)
        (vla-regen cp:doc 1)
        (princ (cp:ru '(1050 1086 1084 1087 1086 1085 1086 1074 1082 1072 32 1088 1072 1079 1076 1077 1083 1077 1085 1072 32 1085 1072 32 1086 1090 1076 1077 1083 1100 1085 1099 1077 32 1086 1073 1098 1077 1082 1090 1099 46))))))
  (princ))
(princ "\nSX_Panel v2.07: CPDRAW / CPUPDATE / CPEDIT / CPDELETE / CPEXPLODE")
(princ)
